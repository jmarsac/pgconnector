Attribute VB_Name = "ClassIChangeTrack"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'/*MAN______________________________________________________________________
'
'
' FICHIER: $RCSfile$ $Revision$
'
'  $Author$  $Date$
'
' DESCRIPTION
' xxxxxxxxxxxxx
'
'
' FONCTIONS
' VOIR EGALEMENT
'
' Copyright   Azimut    Tous droits réservés
' Azimut S.A.R.L 3 rue du travail 67000 Strasbourg
' Tél 03 88 08 50 67
' SIREN 390 458 164   http://www.azimut.fr          grc@azimut.fr
'
'___________________________________________________________________ENDMAN*/
Option Explicit

Implements IChangeTrackEvents

Private Sub IChangeTrackEvents_BeginUndoRedo(ByVal AfterUndoRedo As Element, ByVal BeforeUndoRedo As Element, ByVal Action As MsdChangeTrackAction, ByVal IsUndo As Boolean)
End Sub
Private Sub IChangeTrackEvents_ElementChanged(ByVal AfterChange As Element, ByVal BeforeChange As Element, ByVal Action As MsdChangeTrackAction, CantBeUndone As Boolean)
    Dim s_sql As String
    Dim tablename As String
    Dim wkt As String
    Dim entitynum As Integer
    Dim mslink As Long
    Dim rx As Double, ry As Double, orientation As Double
    Dim echelle As Double
    Dim lv As Level
    Dim ee2 As ElementEnumerator

    If Action = msdChangeTrackActionAdd Then
        '  Adding an element. BeforeChange is Nothing
        If Not AfterChange.Level Is Nothing Then
            Set lv = AfterChange.Level
        ElseIf AfterChange.IsCellElement Then
            Set ee2 = AfterChange.AsCellElement.GetSubElements
            Do While ee2.MoveNext
                If Not ee2.Current.Level Is Nothing Then
                    Set lv = ee2.Current.Level
                End If
                Exit Do
            Loop
            Set ee2 = Nothing
        End If
        If Not lv Is Nothing Then
            s_sql = buildSqlSelectTableNameByLevelnameAndCellname(gSchemaName, lv.name)
            tablename = gPgConnexion.SqlQuery(s_sql)
            If tablename <> "" Then
                Debug.Print "Element " & DLongToString(AfterChange.id) & " is valid"
                s_sql = buildSqlSelectLayerEntitynum(tablename)
                entitynum = Val(gPgConnexion.SqlQuery(s_sql))
                If entitynum > 0 Then
                    wkt = OgcGetElementGeomAstext(AfterChange, True)
                    If AfterChange.HasAnyDatabaseLinks = True Then
                        mslink = ElementGetFirstMslink(azidblib.Odbc, AfterChange, entitynum)
                    End If
                    If AfterChange.IsSharedCellElement Then
                        If Application.Matrix3dIsXRotationYRotationZRotationScale(AfterChange.AsSharedCellElement.Rotation, rx, ry, orientation, echelle) = True Then
                            orientation = orientation / Pi * 180
                        End If
                        Call sendDgnCellToPostgis(tablename, AfterChange, AfterChange.AsSharedCellElement.name, orientation, wkt, entitynum, mslink)
                    ElseIf AfterChange.IsCellElement Then
                        If Application.Matrix3dIsXRotationYRotationZRotationScale(AfterChange.AsCellElement.Rotation, rx, ry, orientation, echelle) = True Then
                            orientation = orientation / Pi * 180
                        End If
                        Call sendDgnCellToPostgis(tablename, AfterChange, AfterChange.AsCellElement.name, orientation, wkt, entitynum, mslink)
                    ElseIf AfterChange.IsClosedElement Then
                        Call sendDgnLinearToPostgis(tablename, AfterChange, wkt, entitynum, mslink)
                    ElseIf AfterChange.IsTextElement Then
                        If Application.Matrix3dIsXRotationYRotationZRotationScale(AfterChange.AsTextElement.Rotation, rx, ry, orientation, echelle) = True Then
                            orientation = orientation / Pi * 180
                        End If
                        Call sendDgnTextToPostgis(tablename, AfterChange, AfterChange.AsTextElement.text, AfterChange.AsTextElement.TextStyle.Height _
                                                , orientation, wkt, entitynum, mslink)
                    Else
                        Call sendDgnLinearToPostgis(tablename, AfterChange, wkt, entitynum, mslink)
                    End If
                End If
            End If
        End If

    ElseIf Action = msdChangeTrackActionDelete Then
        '  Deleting an element.   AfterChange is Nothing
        If Not BeforeChange.Level Is Nothing Then
            Debug.Print "Element " & DLongToString(BeforeChange.id) & " is no longer valid in " & tablename
            If BeforeChange.HasAnyDatabaseLinks = True Then
                entitynum = -1
                mslink = ElementGetFirstMslink(azidblib.Odbc, BeforeChange, entitynum)
                If entitynum > 0 And mslink > 0 Then
                    s_sql = buildSqlSelectTablenameByEntitynum(entitynum)
                    tablename = gPgConnexion.SqlQuery(s_sql)
                    If tablename <> "" Then
                        If BeforeChange.IsSharedCellElement Then
                            Call deleteDgnElementInPostgis(tablename, mslink)
                        ElseIf BeforeChange.IsClosedElement Then
                            Call deleteDgnElementInPostgis(tablename, mslink)
                        ElseIf BeforeChange.IsTextElement Then
                            Call deleteDgnElementInPostgis("description", mslink)
                        Else
                            Call deleteDgnElementInPostgis(tablename, mslink)
                        End If
                    End If
                End If
            End If
        End If
    Else
        Debug.Print "Element " & DLongToString(BeforeChange.id) & " action " & Action
    End If
End Sub
Private Sub IChangeTrackEvents_FinishUndoRedo(ByVal IsUndo As Boolean)

End Sub
Private Sub IChangeTrackEvents_Mark()

End Sub

Attribute VB_Name = "ClassLaunchIChangeHandler"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'___________________________________________________________________________________________________________________________
'NOM :
'DESCRIPTION : classe de contrôle du bon fonctionnement de ClassIChangeTrack
'
'SYNOPSIS
'VOIR EGALEMENT
'DIAGNOSTIC
'________________________________________________________________________________________________

Option Explicit

Implements IChangeTrackEvents


Private Sub IChangeTrackEvents_BeginUndoRedo(ByVal AfterUndoRedo As Element, ByVal BeforeUndoRedo As Element, ByVal Action As MsdChangeTrackAction, ByVal IsUndo As Boolean)
   
   If P_fl_no_elem_events_handle = False Then
      ' Si le traitement des évènements dans ClassIChangeTrack ne s'est pas bien passé, ClassIChangeTrack
      ' n'est plus activée; on vérifie en regardant le contenu de la variable P_fl_elem_events_function_succeeded; si
      ' celle-ci vaut False, ClassIChangeTrack ne s'est pas bien terminée; on la réactive en soustrayant
      ' la classe de la liste des handler puis en la reconstruisant et en l'ajoutant à nouveau
      If P_fl_elem_events_function_succeeded = False Then
         If Not P_elemChangeTrack Is Nothing Then
            RemoveChangeTrackEventsHandler P_elemChangeTrack
         Else
            Set P_elemChangeTrack = New ClassIChangeTrack
         End If
         AddChangeTrackEventsHandler P_elemChangeTrack

      End If
       
      ' Réinitialisation de P_fl_elem_events_function_succeeded
      P_fl_elem_events_function_succeeded = False
   End If
    
End Sub

Private Sub IChangeTrackEvents_ElementChanged(ByVal AfterChange As Element, ByVal BeforeChange As Element, ByVal Action As MsdChangeTrackAction, CantBeUndone As Boolean)
   
   If P_fl_no_elem_events_handle = False Then
      ' Si le traitement des évènements dans ClassIChangeTrack ne s'est pas bien passé, ClassIChangeTrack
      ' n'est plus activée; on vérifie en regardant le contenu de la variable P_fl_elem_events_function_succeeded; si
      ' celle-ci vaut False, ClassIChangeTrack ne s'est pas bien terminée; on la réactive en soustrayant
      ' la classe de la liste des handler puis en la reconstruisant et en l'ajoutant à nouveau
      If P_fl_elem_events_function_succeeded = False Then
         
         If Not P_elemChangeTrack Is Nothing Then
            RemoveChangeTrackEventsHandler P_elemChangeTrack
         Else
            Set P_elemChangeTrack = New ClassIChangeTrack
         End If
         AddChangeTrackEventsHandler P_elemChangeTrack
         
      End If
      
     ' Réinitialisation de P_fl_elem_events_function_succeeded
      P_fl_elem_events_function_succeeded = False
   End If
   
End Sub
Private Sub IChangeTrackEvents_FinishUndoRedo(ByVal IsUndo As Boolean)

End Sub
Private Sub IChangeTrackEvents_Mark()

End Sub

Attribute VB_Name = "ModuleEvents"
'/*MAN______________________________________________________________________
'
'
' FICHIER: $RCSfile$ $Revision$
'
'  $Author$  $Date$
'
' DESCRIPTION
' xxxxxxxxxxxxx
'
'
' FONCTIONS
' VOIR EGALEMENT
'
' Copyright   Azimut    Tous droits réservés
' Azimut S.A.R.L 3 rue du travail 67000 Strasbourg
' Tél 03 88 08 50 67
' SIREN 390 458 164   http://www.azimut.fr          grc@azimut.fr
'
'___________________________________________________________________ENDMAN*/
Option Explicit

'_________________________________________________________________________________________________________________
'NOM : GetElemsEventHandlerTemporaryStopStatus
'DESCRIPTION : renvoie si le traitement des évènements de modif sur les éléments est stoppé ou non
'
'SYNOPSIS
'VOIR EGALEMENT
'DIAGNOSTIC
'_______________________________________________________________________
Public Function GetElemsEventHandlerTemporaryStopStatus() As Boolean
   GetElemsEventHandlerTemporaryStopStatus = P_fl_no_elem_events_handle
End Function

'_________________________________________________________________________________________________________________
'NOM : SetElemsEventHandlerTemporaryStopStatus
'DESCRIPTION : Fixe l'état du traitement des évènements de modif sur les éléments (stoppé ou non)
'
'SYNOPSIS
'VOIR EGALEMENT
'DIAGNOSTIC
'_______________________________________________________________________
Public Sub SetElemsEventHandlerTemporaryStopStatus(status As Boolean)
   P_fl_no_elem_events_handle = status
End Sub

'_________________________________________________________________________________________________________________
'NOM : ElemsEventHandlerTemporaryStop
'DESCRIPTION : stoppe temporairement le traitement des évènements de modif sur les éléments (mais pas l'appel
'              à la fonction
'SYNOPSIS
'VOIR EGALEMENT
'DIAGNOSTIC
'_______________________________________________________________________
Public Sub ElemsEventHandlerTemporaryStop()
   P_fl_no_elem_events_handle = True
End Sub

'_________________________________________________________________________________________________________________
'NOM : ElemsEventHandlerCancelTemporaryStop
'DESCRIPTION : relance le traitement des évènements de modif sur les éléments
'SYNOPSIS
'VOIR EGALEMENT
'DIAGNOSTIC
'_______________________________________________________________________
Public Sub ElemsEventHandlerCancelTemporaryStop()
   P_fl_no_elem_events_handle = False
End Sub



'_________________________________________________________________________________________________________________
'NOM : InitElemsEventHandler
'DESCRIPTION : lance le traitement des évènements de modif sur les éléments
'SYNOPSIS
'VOIR EGALEMENT
'DIAGNOSTIC
'_______________________________________________________________________
Sub InitElemsEventHandler()
   Dim response As String
   
   Call StopElemsEventHandler
   
   If Not gPgConnexion Is Nothing Then
      If gPgConnexion.EstConnecte = True Then
      ' classe de suivi du bon chargement de la classe P_elemChangeTrack
      Set P_launchElemChangeTrack = New ClassLaunchIChangeHandler
      AddChangeTrackEventsHandler P_launchElemChangeTrack
      ' classe du suivi des modifications sur les éléments
      Set P_elemChangeTrack = New ClassIChangeTrack
      AddChangeTrackEventsHandler P_elemChangeTrack
      
      P_fl_elem_events_function_succeeded = True
      P_fl_no_elem_events_handle = False
    End If
   End If

End Sub

'_________________________________________________________________________________________________________________
'NOM : StopElemsEventHandler
'DESCRIPTION : stoppe le traitement des évènements de modif sur les éléments
'SYNOPSIS
'VOIR EGALEMENT
'DIAGNOSTIC
'_______________________________________________________________________
Sub StopElemsEventHandler()
   
   If Not P_elemChangeTrack Is Nothing Then
      RemoveChangeTrackEventsHandler P_elemChangeTrack
   End If
   If Not P_launchElemChangeTrack Is Nothing Then
      RemoveChangeTrackEventsHandler P_launchElemChangeTrack
   End If
   
   Set P_elemChangeTrack = Nothing
   Set P_launchElemChangeTrack = Nothing
   P_fl_elem_events_function_succeeded = False

End Sub

Attribute VB_Name = "ModuleGlobal"
'/*MAN______________________________________________________________________
'
'
' FICHIER: $RCSfile$ $Revision$
'
'  $Author$  $Date$
'
' DESCRIPTION
' xxxxxxxxxxxxx
'
'
' FONCTIONS
' VOIR EGALEMENT
'
' Copyright   Azimut    Tous droits réservés
' Azimut S.A.R.L 3 rue du travail 67000 Strasbourg
' Tél 03 88 08 50 67
' SIREN 390 458 164   http://www.azimut.fr          grc@azimut.fr
'
'___________________________________________________________________ENDMAN*/
Option Explicit

Public Const PgcVersion = "1.1.3"


'
' Configuration variables :
' PGC_SEED_FULLNAME: nom complet du prototype utilisé ($(_USTN_SITE)seed/seed-postgis.dgn par défaut)
'


Public Enum EnumCheckoutMode
    enuCheckoutModeUnknown = 0
    enuCheckoutModeImport = 1
    enuCheckoutModeAttach = 2
End Enum

Public Enum EnumPostgisDgnResetLevel
    enuPostgisDgnResetNone = 0
    enuPostgisDgnResetLayerOnly = 1
    enuPostgisDgnResetFullFile = 2
End Enum

Public Enum EnumGeomType
    enuGeomTypeUnknown = 0
    enuGeomTypePoint = 1
    enuGeomTypeArea = 2
    enuGeomTypeLine = 3
End Enum

Public Const PostgisDgnRefLogicalName = "_pgis_layer_"
Public Const PgDefaultSrid = 32170

Public Const PgcUserLangFrench = "fr"
Public Const PgcUserLangDutch = "du"

Public gPgcInitDone As Boolean
Public gPgcUserLang As String

Public gSqlWhere As String
Public gSqlWhereFence As String
Public gSqlWhereUser As String
Public gSqlQuery As String
Public gSqlQueryLabels As String
Public gSqlUpsert As String

Public gSchemasArray() As String
Public gSchemaName As String
Public gTableName As String
Public gEntitynum As Integer
Public gCheckoutMode As EnumCheckoutMode
Public gPostgisDgnResetLevel As EnumPostgisDgnResetLevel
Public gLevelName As String
Public gLevel As Level
Public gCellname As String
Public gCellOrientation As Double
Public gTextOrientation As Double
Public gTextSize As Double
Public gTablenames As Collection

Public gPgSrid As Long

Public gPgConnexion As azidblib.aziDbConnexion
Public gPgCnxList As String
Public gPgConnectionName As String
Public gPgHost As String
Public gPgPort As String
Public gPgDbname As String
Public gPgUsername As String
Public gPgPassword As String

Public gUseSharedCell As Boolean

' variable de suspension momentanée de la gestion des modifications d'élément (synchro dao->SIG et topologie)
Public P_fl_no_elem_events_handle As Boolean
Public P_launchElemChangeTrack As ClassLaunchIChangeHandler
Public P_elemChangeTrack As ClassIChangeTrack
' variable de vérification si la fonction de gestion des modifications d'élément s'est bien déroulée
Public P_fl_elem_events_function_succeeded As Boolean
Public P_last_deleted_elem As Element
Public P_last_deleted_elem_id As DLong
Public P_soft_deleted_and_created_elem_id As DLong
Public P_fl_deleted_and_created As Boolean
Public P_last_deleted_and_created_mslink As Long

Attribute VB_Name = "ModuleL10n"
'/*MAN______________________________________________________________________
'
'
' FICHIER: $RCSfile$ $Revision$
'
'  $Author$  $Date$
'
' DESCRIPTION
' xxxxxxxxxxxxx
'
'
' FONCTIONS
' VOIR EGALEMENT
'
' Copyright   Azimut    Tous droits réservés
' Azimut S.A.R.L 3 rue du travail 67000 Strasbourg
' Tél 03 88 08 50 67
' SIREN 390 458 164   http://www.azimut.fr          grc@azimut.fr
'
'___________________________________________________________________ENDMAN*/
Option Explicit

Public Const TXT_IMPORTEE_DANS_LE_MODELE_ACTIF = "1"
Public Const TXT_CLAUSE_WHERE = "2"
Public Const TXT_ACTION = "3"
Public Const TXT_AUCUNE_TABLE_N_EST_DISPONIBLE_OU_BIEN_VOUS_N_AVEZ_AUCUN_DROIT_DE_CONSULTATION_SUR_LES_TABLES_EXISTANTES = "4"
Public Const TXT_ATTACHER_COUCHE_POSTGIS_EN_REFERENCE = "5"
Public Const TXT_AUCUNE = "6"
Public Const TXT_AUCUNE_CONNEXION_DEFINIE_VEUILLEZ_EN_CREER_UNE = "7"
Public Const TXT_B_D = "8"
Public Const TXT_CELLULE = "9"
Public Const TXT_CHOIX_COUCHE_POSTGIS = "10"
Public Const TXT_CONNECTE_A_LA_BD = "11"
Public Const TXT_CONNECTER = "12"
Public Const TXT_CONNEXION = "13"
Public Const TXT_CONNEXION_A_LA_BD_REUSSIE = "14"
Public Const TXT_CONNEXION_INVALIDE = "15"
Public Const TXT_CONTACTEZ_L_ADMINISTRATEUR = "16"
Public Const TXT_COPIEZ_LE_DANS_USTN_SITE_SEED_OU_DEFINISSEZ_CORRECTEMENT_LA_VARIABLE_PGC_SEED_FULLNAME = "17"
Public Const TXT_COUCHE = "18"
Public Const TXT_COUCHE_SEULEMENT = "19"
Public Const TXT_COUCHES_POSTGIS = "20"
Public Const TXT_COULEUR = "21"
Public Const TXT_DANS_LE_MODELE_ACTIF = "22"
Public Const TXT_DECONNECTE_DE_LA_BD = "23"
Public Const TXT_DETACHER_LES_COUCHES_POSTGIS = "24"
Public Const TXT_ECHEC_CONNEXION_CONTACTEZ_L_ADMINISTRATEUR = "25"
Public Const TXT_ECHEC_DE_L_IMPORT_DE_LA_COUCHE_POSTGIS = "26"
Public Const TXT_ECHEC_DE_LA_CONNEXION = "27"
Public Const TXT_ECHEC_DE_LA_CONNEXION_A_LA_BD = "28"
Public Const TXT_ELEMENT = "29"
Public Const TXT_ENREGISTRER = "30"
Public Const TXT_ERREUR = "31"
Public Const TXT_EST_INTROUVABLE = "32"
Public Const TXT_EST_VALIDE = "33"
Public Const TXT_EXPORT = "34"
Public Const TXT_EXPORTER = "35"
Public Const TXT_FICHIER_ENTIER = "36"
Public Const TXT_FICHIER_PROTOTYPE_INTROUVABLE = "37"
Public Const TXT_FILTRE = "38"
Public Const TXT_IDENTIFICATION = "39"
Public Const TXT_IMPORTER_COUCHE_POSTGIS = "40"
Public Const TXT_IMPOSSIBLE_DE_SE_CONNECTER_A_LA_BASE_DE_DONNEES_CONTACTEZ_L_ADMINISTRATEUR_POUR_RESOUDRE_LE_PROBLEME = "41"
Public Const TXT_INDIQUER_UN_NOM_POUR_LA_CONNEXION = "42"
Public Const TXT_LE_FICHIER = "43"
Public Const TXT_LE_MODELE_EST_EN_LECTURE_SEULE = "44"
Public Const TXT_MOT_DE_PASSE = "45"
Public Const TXT_NE_PEUT_ETRE_OUVERT = "46"
Public Const TXT_NE_PEUT_ETRE_REINITIALISE = "47"
Public Const TXT_N_EST_PLUS_VALIDE = "48"
Public Const TXT_NIVEAU = "49"
Public Const TXT_NOM = "50"
Public Const TXT_OK = "51"
Public Const TXT_OUVERTURE_DU_FICHIER_IMPOSSIBLE = "52"
Public Const TXT_PORT = "53"
Public Const TXT_POUR_UTILISER_CETTE_COMMANDE_VOUS_DEVEZ_ETRE_CONNECTE_A_LA_BD = "54"
Public Const TXT_QUITTER = "55"
Public Const TXT_REINITIALISATION_DU_FICHIER_IMPOSSIBLE = "56"
Public Const TXT_REINITIALISER = "57"
Public Const TXT_SCHEMA = "58"
Public Const TXT_SERVEUR = "59"
Public Const TXT_SYNCHRONISATION_BD_SPATIALE_ACTIVEE = "60"
Public Const TXT_SYNCHRONISATION_BD_SPATIALE_DESACTIVEE = "61"
Public Const TXT_TABLE = "62"
Public Const TXT_TABLES = "63"
Public Const TXT_TESTER_LA_CONNEXION = "64"
Public Const TXT_TOUS = "65"
Public Const TXT_TOUTES_LES_COUCHES_POSTGIS_DISPARAITRONT = "66"
Public Const TXT_UTILISATEUR = "67"
Public Const TXT_UTILISER_CLOTURE = "68"
Public Const TXT_VOULEZ_VOUS_DETACHER_LE_FICHIER = "69"
Public Const TXT_VUES = "70"
Public Const TXT_LABELS = "71"
Public Const TXT_MODE_SSL = "72"
Public Const TXT_COUCHE_POSTGIS_INTROUVABLE = "73"
Public Const TXT_DANS_LA_TABLE_DESCRIPTION = "74"
Public Const TXT_ERREUR_CONNEXION_OBJET_A_LA_BD = "75"
Public Const TXT_SUPPRIMER_CONNEXION = "76"

Private l10nColl As Collection
Private duColl As Collection

Public Sub l10nInit()
    
    gPgcUserLang = PgcUserLangFrench
    If Application.ActiveWorkspace.IsConfigurationVariableDefined("PGC_USER_LANG") Then
        gPgcUserLang = Application.ActiveWorkspace.ConfigurationVariableValue("PGC_USER_LANG")
        If gPgcUserLang <> PgcUserLangFrench And gPgcUserLang <> PgcUserLangDutch Then
            Application.MessageCenter.AddMessage "Langue inconnue", gPgcUserLang + " est inconnu. Le français sera utilisé.", msdMessageCenterPriorityWarning, True
            gPgcUserLang = PgcUserLangFrench
        End If
    End If
    l10nLoad (gPgcUserLang)

End Sub
Public Sub l10nLoad(langId As String)

Set l10nColl = Nothing
Set l10nColl = New Collection

If langId = PgcUserLangDutch Then
    l10nColl.Add "ingevoerd in het actieve model", TXT_IMPORTEE_DANS_LE_MODELE_ACTIF
    l10nColl.Add " (WHERE clausule)", TXT_CLAUSE_WHERE
    l10nColl.Add "aktie", TXT_ACTION
    l10nColl.Add "Er is geen tabel beschikbaar of u heeft geen rechten op de bestaande tabellen", TXT_AUCUNE_TABLE_N_EST_DISPONIBLE_OU_BIEN_VOUS_N_AVEZ_AUCUN_DROIT_DE_CONSULTATION_SUR_LES_TABLES_EXISTANTES
    l10nColl.Add "Koppelen van een postgislaag als referentie", TXT_ATTACHER_COUCHE_POSTGIS_EN_REFERENCE
    l10nColl.Add "Geen enkele", TXT_AUCUNE
    l10nColl.Add "Er is geen verbinding gedefinieerd, gelieve een verbinding te maken", TXT_AUCUNE_CONNEXION_DEFINIE_VEUILLEZ_EN_CREER_UNE
    l10nColl.Add "DB", TXT_B_D
    l10nColl.Add "Cel", TXT_CELLULE
    l10nColl.Add "Keuze Postgis laag", TXT_CHOIX_COUCHE_POSTGIS
    l10nColl.Add "Gekoppeld met de database", TXT_CONNECTE_A_LA_BD
    l10nColl.Add "Verbinden", TXT_CONNECTER
    l10nColl.Add "Verbinding", TXT_CONNEXION
    l10nColl.Add "Verbinding met de database geslaagd", TXT_CONNEXION_A_LA_BD_REUSSIE
    l10nColl.Add "Ongeldige verbinding", TXT_CONNEXION_INVALIDE
    l10nColl.Add "Contacteer de beheerder", TXT_CONTACTEZ_L_ADMINISTRATEUR
    l10nColl.Add "Kopiëer  in de $(_ustn_site)seed of definieer de variable   PGC_SEED_FULLNAME", TXT_COPIEZ_LE_DANS_USTN_SITE_SEED_OU_DEFINISSEZ_CORRECTEMENT_LA_VARIABLE_PGC_SEED_FULLNAME
    l10nColl.Add "Laag", TXT_COUCHE
    l10nColl.Add "Enkel de laag", TXT_COUCHE_SEULEMENT
    l10nColl.Add "Postgis lagen", TXT_COUCHES_POSTGIS
    l10nColl.Add "kleur", TXT_COULEUR
    l10nColl.Add "in het aktieve model", TXT_DANS_LE_MODELE_ACTIF
    l10nColl.Add "Loskoppelen van de database", TXT_DECONNECTE_DE_LA_BD
    l10nColl.Add "Loskoppelen van de postgis lagen", TXT_DETACHER_LES_COUCHES_POSTGIS
    l10nColl.Add "Verbindingsfout, contacteer de beheerder", TXT_ECHEC_CONNEXION_CONTACTEZ_L_ADMINISTRATEUR
    l10nColl.Add "Fout bij importeren van de postgis laag", TXT_ECHEC_DE_L_IMPORT_DE_LA_COUCHE_POSTGIS
    l10nColl.Add "Verbindingsfout ", TXT_ECHEC_DE_LA_CONNEXION
    l10nColl.Add "Verbindingsfout bij de database", TXT_ECHEC_DE_LA_CONNEXION_A_LA_BD
    l10nColl.Add "element", TXT_ELEMENT
    l10nColl.Add "Bewaren", TXT_ENREGISTRER
    l10nColl.Add "Fout bij importeren van de postgis laag", TXT_ERREUR
    l10nColl.Add "onvindbaar", TXT_EST_INTROUVABLE
    l10nColl.Add "Geldig", TXT_EST_VALIDE
    l10nColl.Add "Export", TXT_EXPORT
    l10nColl.Add "Exporteren", TXT_EXPORTER
    l10nColl.Add "Volledige bestand", TXT_FICHIER_ENTIER
    l10nColl.Add "Seed file onvindbaar", TXT_FICHIER_PROTOTYPE_INTROUVABLE
    l10nColl.Add "filter", TXT_FILTRE
    l10nColl.Add "identificatie", TXT_IDENTIFICATION
    l10nColl.Add "Importeren van een Postgis laag", TXT_IMPORTER_COUCHE_POSTGIS
    l10nColl.Add "Onmogelijk te verbinden met de database, contacteer de beheerder om dit probleem op te lossen", TXT_IMPOSSIBLE_DE_SE_CONNECTER_A_LA_BASE_DE_DONNEES_CONTACTEZ_L_ADMINISTRATEUR_POUR_RESOUDRE_LE_PROBLEME
    l10nColl.Add "Geef de naam van de connectie", TXT_INDIQUER_UN_NOM_POUR_LA_CONNEXION
    l10nColl.Add "het bestand", TXT_LE_FICHIER
    l10nColl.Add "Alleen lezen model", TXT_LE_MODELE_EST_EN_LECTURE_SEULE
    l10nColl.Add "Paswoord", TXT_MOT_DE_PASSE
    l10nColl.Add "Kan niet openen", TXT_NE_PEUT_ETRE_OUVERT
    l10nColl.Add "Kan niet initialiseren", TXT_NE_PEUT_ETRE_REINITIALISE
    l10nColl.Add "Niet meer geldig", TXT_N_EST_PLUS_VALIDE
    l10nColl.Add "Laag", TXT_NIVEAU
    l10nColl.Add "Naam", TXT_NOM
    l10nColl.Add "OK", TXT_OK
    l10nColl.Add "Kan het bestand niet openen", TXT_OUVERTURE_DU_FICHIER_IMPOSSIBLE
    l10nColl.Add "Poort", TXT_PORT
    l10nColl.Add "Dit commando vereist een connectie met de database", TXT_POUR_UTILISER_CETTE_COMMANDE_VOUS_DEVEZ_ETRE_CONNECTE_A_LA_BD
    l10nColl.Add "Afsluiten", TXT_QUITTER
    l10nColl.Add "Herinitialisatie van het bestand niet mogelijk", TXT_REINITIALISATION_DU_FICHIER_IMPOSSIBLE
    l10nColl.Add "Herinitialiseren", TXT_REINITIALISER
    l10nColl.Add "Schema", TXT_SCHEMA
    l10nColl.Add "Server", TXT_SERVEUR
    l10nColl.Add "Synchronisatie met de Spatial database is aktief", TXT_SYNCHRONISATION_BD_SPATIALE_ACTIVEE
    l10nColl.Add "Synchronisatie met de Spatial database is niet aktief", TXT_SYNCHRONISATION_BD_SPATIALE_DESACTIVEE
    l10nColl.Add "Tabel", TXT_TABLE
    l10nColl.Add "Tabellen", TXT_TABLES
    l10nColl.Add "Testen van de connectie", TXT_TESTER_LA_CONNEXION
    l10nColl.Add "Alle", TXT_TOUS
    l10nColl.Add "Alle Postgis lagen zullen verdwijnen", TXT_TOUTES_LES_COUCHES_POSTGIS_DISPARAITRONT
    l10nColl.Add "Gebruiker", TXT_UTILISATEUR
    l10nColl.Add "Gebruik het Fence commando", TXT_UTILISER_CLOTURE
    l10nColl.Add "Wil je het bestand loskoppelen", TXT_VOULEZ_VOUS_DETACHER_LE_FICHIER
    l10nColl.Add "Vensters", TXT_VUES
    l10nColl.Add "Labels", TXT_LABELS
    l10nColl.Add "SSL mode", TXT_MODE_SSL
    l10nColl.Add "Postgis laag onvindbaar", TXT_COUCHE_POSTGIS_INTROUVABLE
    l10nColl.Add " in 'description' tabel", TXT_DANS_LA_TABLE_DESCRIPTION
    l10nColl.Add "Verbindingsfout ", TXT_ERREUR_CONNEXION_OBJET_A_LA_BD
    l10nColl.Add "Verwijderen verbinding", TXT_SUPPRIMER_CONNEXION
    
Else
    l10nColl.Add " importée dans le modèle actif", TXT_IMPORTEE_DANS_LE_MODELE_ACTIF
    l10nColl.Add "(clause WHERE)", TXT_CLAUSE_WHERE
    l10nColl.Add "action", TXT_ACTION
    l10nColl.Add "Aucune table n'est disponible ou bien vous n'avez aucun droit de consultation sur les tables existantes", TXT_AUCUNE_TABLE_N_EST_DISPONIBLE_OU_BIEN_VOUS_N_AVEZ_AUCUN_DROIT_DE_CONSULTATION_SUR_LES_TABLES_EXISTANTES
    l10nColl.Add "Attacher couche PostGIS en référence", TXT_ATTACHER_COUCHE_POSTGIS_EN_REFERENCE
    l10nColl.Add "Aucune", TXT_AUCUNE
    l10nColl.Add "Aucune connexion définie. Veuillez en créer une.", TXT_AUCUNE_CONNEXION_DEFINIE_VEUILLEZ_EN_CREER_UNE
    l10nColl.Add "B.D.", TXT_B_D
    l10nColl.Add "Cellule", TXT_CELLULE
    l10nColl.Add "Choix couche PostGIS", TXT_CHOIX_COUCHE_POSTGIS
    l10nColl.Add "Connecté à la BD", TXT_CONNECTE_A_LA_BD
    l10nColl.Add "Connecter", TXT_CONNECTER
    l10nColl.Add "Connexion", TXT_CONNEXION
    l10nColl.Add "Connexion à la BD réussie", TXT_CONNEXION_A_LA_BD_REUSSIE
    l10nColl.Add "Connexion invalide", TXT_CONNEXION_INVALIDE
    l10nColl.Add "Contactez l'administrateur.", TXT_CONTACTEZ_L_ADMINISTRATEUR
    l10nColl.Add "Copiez le dans $(_ustn_site)seed ou définissez correctement la variable PGC_SEED_FULLNAME", TXT_COPIEZ_LE_DANS_USTN_SITE_SEED_OU_DEFINISSEZ_CORRECTEMENT_LA_VARIABLE_PGC_SEED_FULLNAME
    l10nColl.Add "Couche", TXT_COUCHE
    l10nColl.Add "Couche seulement", TXT_COUCHE_SEULEMENT
    l10nColl.Add "Couches PostGIS", TXT_COUCHES_POSTGIS
    l10nColl.Add "Couleur", TXT_COULEUR
    l10nColl.Add " dans le modèl actif", TXT_DANS_LE_MODELE_ACTIF
    l10nColl.Add "Déconnecté de la BD", TXT_DECONNECTE_DE_LA_BD
    l10nColl.Add "Détacher les couches PotGIS", TXT_DETACHER_LES_COUCHES_POSTGIS
    l10nColl.Add "Echec connexion. Contactez l'administrateur", TXT_ECHEC_CONNEXION_CONTACTEZ_L_ADMINISTRATEUR
    l10nColl.Add "Echec de l'import de la couche PostGIS", TXT_ECHEC_DE_L_IMPORT_DE_LA_COUCHE_POSTGIS
    l10nColl.Add "Echec de la connexion", TXT_ECHEC_DE_LA_CONNEXION
    l10nColl.Add "Echec de la connexion à la BD", TXT_ECHEC_DE_LA_CONNEXION_A_LA_BD
    l10nColl.Add "Elément", TXT_ELEMENT
    l10nColl.Add "Enregistrer", TXT_ENREGISTRER
    l10nColl.Add "Erreur", TXT_ERREUR
    l10nColl.Add "est introuvable", TXT_EST_INTROUVABLE
    l10nColl.Add "est valide", TXT_EST_VALIDE
    l10nColl.Add "Export", TXT_EXPORT
    l10nColl.Add "Exporter", TXT_EXPORTER
    l10nColl.Add "Fichier entier", TXT_FICHIER_ENTIER
    l10nColl.Add "Fichier prototype introuvable", TXT_FICHIER_PROTOTYPE_INTROUVABLE
    l10nColl.Add "Filtre", TXT_FILTRE
    l10nColl.Add "Identification", TXT_IDENTIFICATION
    l10nColl.Add "Importer couche PostGIS", TXT_IMPORTER_COUCHE_POSTGIS
    l10nColl.Add "Impossible de se connecter à la base de données. Contactez l'administrateur pour résoudre le problème. ", TXT_IMPOSSIBLE_DE_SE_CONNECTER_A_LA_BASE_DE_DONNEES_CONTACTEZ_L_ADMINISTRATEUR_POUR_RESOUDRE_LE_PROBLEME
    l10nColl.Add "Indiquer un nom pour la connexion", TXT_INDIQUER_UN_NOM_POUR_LA_CONNEXION
    l10nColl.Add "Le fichier", TXT_LE_FICHIER
    l10nColl.Add "Le modèle est en lecture seule", TXT_LE_MODELE_EST_EN_LECTURE_SEULE
    l10nColl.Add "Mot de passe", TXT_MOT_DE_PASSE
    l10nColl.Add "ne peut être ouvert", TXT_NE_PEUT_ETRE_OUVERT
    l10nColl.Add "ne peut être réinitialisé", TXT_NE_PEUT_ETRE_REINITIALISE
    l10nColl.Add "n'est plus valide", TXT_N_EST_PLUS_VALIDE
    l10nColl.Add "Niveau", TXT_NIVEAU
    l10nColl.Add "Nom", TXT_NOM
    l10nColl.Add "OK", TXT_OK
    l10nColl.Add "Ouverture du fichier impossible", TXT_OUVERTURE_DU_FICHIER_IMPOSSIBLE
    l10nColl.Add "Port", TXT_PORT
    l10nColl.Add "Pour utiliser cette commande, vous devez être connecté à la BD.", TXT_POUR_UTILISER_CETTE_COMMANDE_VOUS_DEVEZ_ETRE_CONNECTE_A_LA_BD
    l10nColl.Add "Quitter", TXT_QUITTER
    l10nColl.Add "Réinitialisation du fichier impossible", TXT_REINITIALISATION_DU_FICHIER_IMPOSSIBLE
    l10nColl.Add "Réinitialiser", TXT_REINITIALISER
    l10nColl.Add "Schéma", TXT_SCHEMA
    l10nColl.Add "Serveur", TXT_SERVEUR
    l10nColl.Add "Synchronisation BD spatiale activée", TXT_SYNCHRONISATION_BD_SPATIALE_ACTIVEE
    l10nColl.Add "Synchronisation BD spatiale desactivée", TXT_SYNCHRONISATION_BD_SPATIALE_DESACTIVEE
    l10nColl.Add "Table", TXT_TABLE
    l10nColl.Add "Tables", TXT_TABLES
    l10nColl.Add "Tester la connexion", TXT_TESTER_LA_CONNEXION
    l10nColl.Add "Tous", TXT_TOUS
    l10nColl.Add "Toutes les couches PostGIS disparaitront", TXT_TOUTES_LES_COUCHES_POSTGIS_DISPARAITRONT
    l10nColl.Add "Utilisateur", TXT_UTILISATEUR
    l10nColl.Add "Utiliser clôture", TXT_UTILISER_CLOTURE
    l10nColl.Add "Voulez-vous détacher le fichier", TXT_VOULEZ_VOUS_DETACHER_LE_FICHIER
    l10nColl.Add "Vues", TXT_VUES
    l10nColl.Add "Etiquettes", TXT_LABELS
    l10nColl.Add "Mode SSL", TXT_MODE_SSL
    l10nColl.Add "Couche PostGIS introuvable", TXT_COUCHE_POSTGIS_INTROUVABLE
    l10nColl.Add " dans la table 'description'", TXT_DANS_LA_TABLE_DESCRIPTION
    l10nColl.Add "Erreur de connexion de l'objet à la B.D.", TXT_ERREUR_CONNEXION_OBJET_A_LA_BD
    l10nColl.Add "Supprimer connexion", TXT_SUPPRIMER_CONNEXION

End If

End Sub
Public Function l10n(txtId As String) As String
    On Error Resume Next
    l10n = l10nColl(txtId)
    On Error GoTo 0
End Function

Attribute VB_Name = "ModuleLib"
'/*MAN______________________________________________________________________
'
'
' FICHIER: $RCSfile$ $Revision$
'
'  $Author$  $Date$
'
' DESCRIPTION
' xxxxxxxxxxxxx
'
'
' FONCTIONS
' VOIR EGALEMENT
'
' Copyright   Azimut    Tous droits réservés
' Azimut S.A.R.L 3 rue du travail 67000 Strasbourg
' Tél 03 88 08 50 67
' SIREN 390 458 164   http://www.azimut.fr          grc@azimut.fr
'
'___________________________________________________________________ENDMAN*/
Option Explicit

Declare Sub mdlElmdscr_setProperties Lib "stdmdlbltin.dll" (ByVal edP As Long, ByVal Level As Long, ByVal ggNum As Long, ByVal elementClass As Long, ByVal locked As Long, ByVal newElm As Long, ByVal modified As Long, ByVal viewIndepend As Long, ByVal solidHole As Long)

Public Function checkOpenConnection(ByRef azicnx As azidblib.aziDbConnexion, host As String, PORT As String, dbname As String, username As String, password As String) As Boolean
Dim pgOdbcDriver As String

pgOdbcDriver = "PostgreSQL Unicode"
If Application.ActiveWorkspace.IsConfigurationVariableDefined("PGC_ODBC_DRIVER") = True Then
    pgOdbcDriver = Application.ActiveWorkspace.ConfigurationVariableValue("PGC_ODBC_DRIVER")
End If

If azicnx.CONNEXION.State = adStateOpen Then
    checkOpenConnection = True
    Exit Function
End If
If host <> "" And PORT <> "" And dbname <> "" And username <> "" And password <> "" Then
    azicnx.CONNEXION.ConnectionString = "Driver=" + pgOdbcDriver + ";Server=" + host _
            + ";Port=" + PORT _
            + ";Database=" + dbname _
            + ";Uid=" + username _
            + ";Pwd=" + password + ";"
    On Error GoTo erreur
    If azicnx.CONNEXION.State <> adStateOpen Then
        azicnx.CONNEXION.Open
    End If
    checkOpenConnection = True
    azicnx.FormatBD = PostgreSQL
    azicnx.TypeBD = azidblib.conTxtDBProviderPostgreSQLOdbc

    Exit Function
erreur:
   checkOpenConnection = False
End If
End Function
Public Function buildPostgisDgnFilename(Optional ByVal fullDgnFilename As String = "") As String
Dim fullname As String

If fullDgnFilename = "" Then
    fullname = Application.ActiveDesignFile.fullname
Else
    fullname = fullDgnFilename
End If
buildPostgisDgnFilename = Replace(fullname, ".dgn", "-pgis.dgn")
buildPostgisDgnFilename = Replace(buildPostgisDgnFilename, ".DGN", "-pgis.DGN")
buildPostgisDgnFilename = Replace(buildPostgisDgnFilename, ".dwg", "-pgis.dwg")
buildPostgisDgnFilename = Replace(buildPostgisDgnFilename, ".DWG", "-pgis.DWG")

End Function
Public Function removeElementsByLevelInModel(mref As ModelReference, lv As Level) As Boolean
Dim esc As New ElementScanCriteria
Dim ee As ElementEnumerator, ee2 As ElementEnumerator
Dim vf As Boolean

esc.Reset
esc.ExcludeNonGraphical
Set ee = mref.Scan(esc)
Do While ee.MoveNext
    If ee.Current.Type = msdElementTypeCellHeader Then
        Set ee2 = ee.Current.AsCellElement.GetSubElements
        Do While ee.MoveNext
            If ee.Current.Level.name = lv.name Then
                vf = True
            Else
                vf = False
            End If
            Exit Do
        Loop
        Set ee2 = Nothing
        If vf = True Then
            mref.RemoveElement ee.Current
        End If
    Else
        If ee.Current.Level.name = lv.name Then
            mref.RemoveElement ee.Current
        End If
    End If
Loop
End Function
Public Function writeGisObjectsToModel(mref As ModelReference) As Boolean
Dim el As Element
Dim rs As ADODB.Recordset
Dim cc As CopyContext
Dim init_done As Boolean
Dim cellname As String
Dim is_orientable As Boolean
Dim desc As String
Dim levelname As String
Dim mslink As Long

If mref Is Nothing Then Exit Function

If mref.IsReadOnly = True Then
    Application.MessageCenter.AddMessage l10n(TXT_LE_MODELE_EST_EN_LECTURE_SEULE), , msdMessageCenterPriorityError, True
    Exit Function
End If

gUseSharedCell = IIf(GetCExpressionValue("tcb->ext_locks.sharedCells") = 0, False, True)

If mref.DesignFile.fullname <> Application.ActiveModelReference.DesignFile.fullname Then
    Set cc = New CopyContext
Else
    Set cc = Nothing
End If
If Not gPgConnexion Is Nothing Then
    If gPgConnexion.EstConnecte = True Then
        GoTo suite
    End If
End If
Application.MessageCenter.AddMessage l10n(TXT_POUR_UTILISER_CETTE_COMMANDE_VOUS_DEVEZ_ETRE_CONNECTE_A_LA_BD), , msdMessageCenterPriorityError, True
Exit Function

suite:

If init_done <> True Then
    If getLayerSetting(gSchemaName, gTableName, gCellname, is_orientable, desc, gLevelName) <> True Then
        Application.MessageCenter.AddMessage l10n(TXT_COUCHE_POSTGIS_INTROUVABLE), l10n(TXT_COUCHE) + gTableName + l10n(TXT_EST_INTROUVABLE) + l10n(TXT_DANS_LA_TABLE_DESCRIPTION), msdMessageCenterPriorityWarning, True
    End If
End If
Set gLevel = Application.ActiveDesignFile.Levels.Find(gLevelName)
If Not gLevel Is Nothing And gPostgisDgnResetLevel = enuPostgisDgnResetLayerOnly Then
    Call removeElementsByLevelInModel(mref, gLevel)
End If
If gLevel Is Nothing Then Set gLevel = Application.ActiveDesignFile.Levels(64)
Set Application.ActiveSettings.Level = gLevel

Set Application.ActiveSettings.LineStyle = ByLevelLineStyle
Application.ActiveSettings.LineWeight = -1
Application.ActiveSettings.color = -1
Set rs = New ADODB.Recordset
With rs
    .Open gSqlQuery, gPgConnexion.CONNEXION, adOpenForwardOnly, adLockReadOnly
    If .State = adStateOpen Then
        If .BOF = False Or .EOF = False Then
            Do While Not .EOF
                gCellOrientation = 0#
                If Not IsNull(.Fields("cell_orientation")) Then
                    gCellOrientation = Val(Replace(.Fields("cell_orientation"), ",", "."))
                End If
                Set el = elemFromWkt(.Fields("wkt"))
                mslink = 0
                If Not IsNull(.Fields("gid")) Then
                    mslink = Val(.Fields("gid"))
                End If
                If Not el Is Nothing Then
                    If gEntitynum > 0 And mslink > 0 Then
                        Call ElementDbConnectMslink(azidblib.Odbc, el, mslink, gEntitynum)
                    End If
                    If cc Is Nothing Then
                        Call mref.AddElement(el)
                    Else
                        Call mref.CopyElement(el, cc)
                    End If
                End If
                .MoveNext
            Loop
        End If
        .Close
    End If
End With
writeGisObjectsToModel = True

End Function
Public Function writeGisLabelsToModel(mref As ModelReference) As Boolean
Dim el As Element
Dim rs As ADODB.Recordset
Dim cc As CopyContext
Dim init_done As Boolean
Dim is_orientable As Boolean
Dim desc As String
Dim levelname As String
Dim text As String
Dim size As Double
Dim mslink As Long

If mref Is Nothing Then Exit Function

If mref.IsReadOnly = True Then
    Application.MessageCenter.AddMessage l10n(TXT_LE_MODELE_EST_EN_LECTURE_SEULE), , msdMessageCenterPriorityError, True
    Exit Function
End If

'If mref.DesignFile.fullname <> Application.ActiveModelReference.DesignFile.fullname Then
    Set cc = New CopyContext
'Else
'    Set cc = Nothing
'End If
If Not gPgConnexion Is Nothing Then
    If gPgConnexion.EstConnecte = True Then
        GoTo suite
    End If
End If
Application.MessageCenter.AddMessage l10n(TXT_POUR_UTILISER_CETTE_COMMANDE_VOUS_DEVEZ_ETRE_CONNECTE_A_LA_BD), , msdMessageCenterPriorityError, True
Exit Function

suite:

'If init_done <> True Then
'    If getLayerSetting(gSchemaName, gTableName, gCellname, is_orientable, desc, gLevelName) <> True Then
'        Application.MessageCenter.AddMessage "Couche PostGIS introuvable", "La couche " + gTableName + " est introuvable dans la table description", msdMessageCenterPriorityWarning, True
'    End If
'End If
'Set gLevel = Application.ActiveDesignFile.Levels.Find(gLevelName)
'If Not gLevel Is Nothing And gPostgisDgnResetLevel = enuPostgisDgnResetLayerOnly Then
'    Call removeElementsByLevelInModel(mref, gLevel)
'End If
'If gLevel Is Nothing Then Set gLevel = Application.ActiveDesignFile.Levels(64)
'Set Application.ActiveSettings.Level = gLevel

Set Application.ActiveSettings.LineStyle = Application.ActiveDesignFile.LineStyles.Find("0")
Application.ActiveSettings.LineWeight = 0
Application.ActiveSettings.color = -1
Set rs = New ADODB.Recordset
With rs
    .Open gSqlQueryLabels, gPgConnexion.CONNEXION, adOpenForwardOnly, adLockReadOnly
    If .State = adStateOpen Then
        If .BOF = False Or .EOF = False Then
            Do While Not .EOF
                gTextOrientation = 0#
                If Not IsNull(.Fields("orientation")) Then
                    gTextOrientation = Val(Replace(.Fields("orientation"), ",", "."))
                End If
                size = 1#
                If Not IsNull(.Fields("size")) Then
                    size = Val(Replace(.Fields("size"), ",", "."))
                End If
                If Not IsNull(.Fields("label")) Then
                    text = .Fields("label")
                End If
                If text <> "" Then
                    Application.ActiveSettings.TextStyle.Width = size
                    Application.ActiveSettings.TextStyle.Height = size
                    Set el = textElemFromWkt(.Fields("wkt"), text, gTextOrientation)
                    mslink = 0
                    If Not IsNull(.Fields("gid")) Then
                        mslink = Val(.Fields("gid"))
                    End If
                    If Not el Is Nothing Then
                        If gEntitynum > 0 And mslink > 0 Then
                            Call ElementDbConnectMslink(azidblib.Odbc, el, mslink, gEntitynum)
                        End If
                        If cc Is Nothing Then
                            Call mref.AddElement(el)
                        Else
                            Call mref.CopyElement(el, cc)
                        End If
                    End If
                End If
                .MoveNext
            Loop
        End If
        .Close
    End If
End With
writeGisLabelsToModel = True

End Function
Public Function pgcCreateActiveDgnPostgis(fullname As String) As Boolean
Dim seedfullname As String

If Application.ActiveWorkspace.IsConfigurationVariableDefined("PGC_SEED_FULLNAME") = True Then
    seedfullname = Application.ActiveWorkspace.ExpandConfigurationVariable("PGC_SEED_FULLNAME")
Else
    seedfullname = Application.ActiveWorkspace.ExpandConfigurationVariable("$(_ustn_site)seed/seed-postgis.dgn")
End If
If Not win32api.aziFileMgr.FileExists(seedfullname) Then
    Application.MessageCenter.AddMessage l10n(TXT_FICHIER_PROTOTYPE_INTROUVABLE), l10n(TXT_LE_FICHIER) + vbCrLf + seedfullname + vbCrLf + l10n(TXT_EST_INTROUVABLE) + vbCrLf + l10n(TXT_COPIEZ_LE_DANS_USTN_SITE_SEED_OU_DEFINISSEZ_CORRECTEMENT_LA_VARIABLE_PGC_SEED_FULLNAME), msdMessageCenterPriorityError, True
    Application.CommandState.StartDefaultCommand
    Exit Function
End If
win32api.aziFileMgr.CopierFichier seedfullname, fullname
pgcCreateActiveDgnPostgis = True

End Function
Public Function pgcInit() As Boolean
pgcInit = gPgcInitDone
If gPgcInitDone <> True Then
    Dim s_tmp As String
    
    l10nInit
    If Application.ActiveWorkspace.IsConfigurationVariableDefined("PGC_SCHEMAS") = True Then
        s_tmp = Application.ActiveWorkspace.ExpandConfigurationVariable("PGC_SCHEMAS")
    End If
    If s_tmp = "" Then
        s_tmp = "ev_cad"
    End If
    gSchemasArray = Split(s_tmp, ";")
    gSchemaName = GetSetting("PgConnector", "UserFormSelectLayer", "LastSchemaName", "ev_cad")
End If
End Function
Public Function getLayerSrid(schemaname As String, tablename As String) As Long
Dim s_tmp As String

' SRID
If Not gPgConnexion Is Nothing Then
    If gPgConnexion.EstConnecte = True Then
        s_tmp = gPgConnexion.SqlQuery("SELECT Find_SRID('" + schemaname + "', '" + tablename + "', 'geom')")
        If s_tmp <> "" Then
            getLayerSrid = Val(s_tmp)
        End If
    End If
End If

End Function
Public Function getLayerSetting(schemaname As String, tablename As String _
    , ByRef cellname As String, ByRef is_orientable As Boolean, ByRef desc As String, ByRef levelname As String) As Boolean

Dim s_sql As String

If Not gPgConnexion Is Nothing Then
    If gPgConnexion.EstConnecte = True Then
        s_sql = buildSqlSelectLayerSettings(schemaname, tablename)
        If s_sql <> "" Then
            Dim rs As ADODB.Recordset
            Set rs = New Recordset
            
            cellname = ""
            is_orientable = False
            desc = ""
            levelname = Application.ActiveDesignFile.Levels(64).name
            With rs
                .Open s_sql, gPgConnexion.CONNEXION, adOpenStatic, adLockReadOnly
                If .State = adStateOpen Then
                    If Not (.BOF And .EOF) Then
                        If Not IsNull(.Fields("cell")) Then cellname = .Fields("cell")
                        If Not IsNull(.Fields("cell_orientation")) Then is_orientable = IIf(.Fields("cell_orientation") = "YES", True, False)
                        If Not IsNull(.Fields("abbr_" + gPgcUserLang)) Then desc = .Fields("abbr_" + gPgcUserLang)
                        If Not IsNull(.Fields("layer")) Then levelname = .Fields("layer")
                        getLayerSetting = True
                    End If
                End If
            End With
        End If
    End If
End If

End Function
Public Function ElementGetFirstMslink(linkType As Integer, el As Element, Optional ByRef entitynum As Integer = -1) As Long

Dim to_add As Boolean
Dim dblink_arr() As DatabaseLink
Dim dblink As DatabaseLink

ElementGetFirstMslink = 0
If el.HasAnyDatabaseLinks Then
    If entitynum >= 0 Then
        dblink_arr = el.GetDatabaseLinks(, entitynum)
    Else
        dblink_arr = el.GetDatabaseLinks
    End If
    If UBound(dblink_arr) > -1 Then
        ElementGetFirstMslink = dblink_arr(0).mslink
        If entitynum = -1 Then
            entitynum = dblink_arr(0).EntityNumber
        End If
    End If
End If
      
End Function
'___________________________________________________________________________________________________________________________
'NOM : ElementDbConnectMslink
'DESCRIPTION : renvoie un booleen indiquant que le lien BD a bien été ajouté
'SYNOPSIS
'VOIR EGALEMENT
'DIAGNOSTIC
'___________________________________________________________________________________________________________________________

Public Function ElementDbConnectMslink(linkType As Integer, el As Element, mslink As Long, entitynum As Integer, _
                                Optional rewrite As Boolean = False) As Boolean

    If entitynum = 0 Then
    
    ElementDbConnectMslink = False
    Exit Function
    
    Else
    
        Dim to_add As Boolean
        Dim dblink_arr() As DatabaseLink
        Dim dblink As DatabaseLink
        
        If el.HasAnyDatabaseLinks Then
            dblink_arr = el.GetDatabaseLinks(, entitynum)
            If UBound(dblink_arr) > -1 Then
                If dblink_arr(0).EntityNumber = entitynum Then
                    to_add = True
                    If dblink_arr(0).mslink <> mslink Then
                        If rewrite = False Then
                            ElementDbConnectMslink = False
                            MsgBox l10n(TXT_ERREUR_CONNEXION_OBJET_A_LA_BD)
                            Exit Function
                        Else
                            el.RemoveDatabaseLink dblink_arr(0).DatabaseType, dblink_arr(0).mslink, dblink_arr(0).EntityNumber
                            to_add = True
                        End If
                    ElseIf dblink_arr(0).mslink = mslink Then
                        to_add = False
                    End If
                End If
            Else
                                ' nettoyage de liens incorrects (entitynum nul)
                dblink_arr = el.GetDatabaseLinks(, 0)
                If UBound(dblink_arr) > -1 Then
                    el.RemoveDatabaseLink dblink_arr(0).DatabaseType, dblink_arr(0).mslink, dblink_arr(0).EntityNumber
                End If
                to_add = True
            End If
        Else
            to_add = True
        End If
        If to_add = True Then
            Set dblink = CreateDatabaseLink(mslink, entitynum, linkType, False, 0)
            el.AddDatabaseLink dblink
            If rewrite = True Then el.rewrite
            ElementDbConnectMslink = True
        End If
    
    End If

  
End Function
Public Function sendDgnObjectsToPostgis(lv As Level) As Boolean
Dim esc As ElementScanCriteria
Dim ee As ElementEnumerator, ee2 As ElementEnumerator
Dim vf As Boolean
Dim cellname As String
Dim orientation As Double
Dim size As Double
Dim tablename As String
Dim mslink As Long
Dim entitynum As Integer
Dim s_sql As String
Dim wkt As String
Dim rx As Double, ry As Double, echelle As Double

Call OgcSetPrecisionPlani(3)
Call OgcSetPrecisionAlti(3)

Set esc = New ElementScanCriteria
'esc.ExcludeNonGraphical
'esc.ExcludeAllLevels
'esc.IncludeOnlyVisible
'esc.IncludeLevel lv

Set ee = Application.ActiveModelReference.Scan(esc)
Do While ee.MoveNext
    If ee.Current.IsGraphical Then
    orientation = 0#
    size = 1#
    mslink = 0
    If ee.Current.Type = msdElementTypeCellHeader Then
        Set ee2 = ee.Current.AsCellElement.GetSubElements
        Do While ee2.MoveNext
            If ee2.Current.Level.name = lv.name Then
                vf = True
            Else
                vf = False
            End If
            Exit Do
        Loop
        Set ee2 = Nothing
        If vf = True Then
            s_sql = buildSqlSelectTableNameByLevelnameAndCellname(gSchemaName, lv.name, ee.Current.AsCellElement.name)
            tablename = gPgConnexion.SqlQuery(s_sql)
            s_sql = buildSqlSelectLayerEntitynum(tablename)
            entitynum = Val(gPgConnexion.SqlQuery(s_sql))
            If entitynum > 0 Then
                wkt = OgcGetElementGeomAstext(ee.Current, True)
                If Application.Matrix3dIsXRotationYRotationZRotationScale(ee.Current.AsCellElement.Rotation, rx, ry, orientation, echelle) = True Then
                    orientation = orientation / Pi * 180
                End If
                If ee.Current.HasAnyDatabaseLinks = True Then
                    mslink = ElementGetFirstMslink(azidblib.Odbc, ee.Current, entitynum)
                End If
                Call sendDgnCellToPostgis(tablename, ee.Current, ee.Current.AsCellElement.name, orientation, wkt, entitynum, mslink)
            End If
        End If
    Else
        If ee.Current.Level.name = lv.name Then
            If ee.Current.IsSharedCellElement Then
                s_sql = buildSqlSelectTableNameByLevelnameAndCellname(gSchemaName, lv.name, ee.Current.AsSharedCellElement.name)
                tablename = gPgConnexion.SqlQuery(s_sql)
                If tablename = "" Then
                    s_sql = buildSqlSelectTableNameByLevelnameAndCellname(gSchemaName, lv.name)
                    tablename = gPgConnexion.SqlQuery(s_sql)
                End If
            Else
                s_sql = buildSqlSelectTableNameByLevelnameAndCellname(gSchemaName, lv.name)
                tablename = gPgConnexion.SqlQuery(s_sql)
            End If
            s_sql = buildSqlSelectLayerEntitynum(tablename)
            entitynum = Val(gPgConnexion.SqlQuery(s_sql))
            If entitynum > 0 Then
                wkt = OgcGetElementGeomAstext(ee.Current, True)
                If ee.Current.HasAnyDatabaseLinks = True Then
                    mslink = ElementGetFirstMslink(azidblib.Odbc, ee.Current, entitynum)
                End If
                If ee.Current.IsSharedCellElement Then
                    If Application.Matrix3dIsXRotationYRotationZRotationScale(ee.Current.AsSharedCellElement.Rotation, rx, ry, orientation, echelle) = True Then
                        orientation = orientation / Pi * 180
                    End If
                    Call sendDgnCellToPostgis(tablename, ee.Current, ee.Current.AsSharedCellElement.name, orientation, wkt, entitynum, mslink)
                ElseIf ee.Current.IsClosedElement Then
                    Call sendDgnLinearToPostgis(tablename, ee.Current, wkt, entitynum, mslink)
                ElseIf ee.Current.IsTextElement Then
                    If Application.Matrix3dIsXRotationYRotationZRotationScale(ee.Current.AsTextElement.Rotation, rx, ry, orientation, echelle) = True Then
                        orientation = orientation / Pi * 180
                    End If
                    Call sendDgnTextToPostgis(tablename, ee.Current, ee.Current.AsTextElement.text, ee.Current.AsTextElement.TextStyle.Height _
                                            , orientation, wkt, entitynum, mslink)
                Else
                    Call sendDgnLinearToPostgis(tablename, ee.Current, wkt, entitynum, mslink)
                End If
            End If
        End If
    End If
    End If
Loop
Set ee = Nothing
Set esc = Nothing

End Function
Public Sub elementSetLevel(elem As Element, olevel As Level)
   mdlElmdscr_setProperties elem.MdlElementDescrP, VarPtr(olevel.id), 0, 0, 0, 0, 0, 0, 0
End Sub

Attribute VB_Name = "ModulePg2dgn"
'/*MAN______________________________________________________________________
'
'
' FICHIER: $RCSfile$ $Revision$
'
'  $Author$  $Date$
'
' DESCRIPTION
' xxxxxxxxxxxxx
'
'
' FONCTIONS
' VOIR EGALEMENT
'
' Copyright   Azimut    Tous droits réservés
' Azimut S.A.R.L 3 rue du travail 67000 Strasbourg
' Tél 03 88 08 50 67
' SIREN 390 458 164   http://www.azimut.fr          grc@azimut.fr
'
'___________________________________________________________________ENDMAN*/
Option Explicit

Private nb_decimales_plani As Integer
Private nb_decimales_alti As Integer
Private fmt_plani As String
Private fmt_alti As String

'
'NOM : OgcSetPrecisionPlani
'DESCRIPTION : définit le nombre de décimales pour les x,y des géométries OGC
'SYNOPSIS
'VOIR EGALEMENT
'DIAGNOSTIC
'___________________________________________________________________________________________________________________________
Public Sub OgcSetPrecisionPlani(nb_decimales As Integer)
If nb_decimales <> nb_decimales_plani Then
    nb_decimales_plani = nb_decimales
    If nb_decimales = 0 Then
        fmt_plani = "######0"
    ElseIf nb_decimales = 1 Then
        fmt_plani = "######0.#"
    ElseIf nb_decimales = 2 Then
        fmt_plani = "######0.##"
    ElseIf nb_decimales = 3 Then
        fmt_plani = "######0.###"
    ElseIf nb_decimales = 4 Then
        fmt_plani = "######0.####"
    ElseIf nb_decimales = 5 Then
        fmt_plani = "######0.#####"
    End If
End If
End Sub

'NOM : OgcSetPrecisionAlti
'DESCRIPTION : définit le nombre de décimales pour les z des géométries OGC
'SYNOPSIS
'VOIR EGALEMENT
'DIAGNOSTIC
'___________________________________________________________________________________________________________________________
Public Sub OgcSetPrecisionAlti(nb_decimales As Integer)
If nb_decimales <> nb_decimales_alti Then
    nb_decimales_alti = nb_decimales
    If nb_decimales = 0 Then
        fmt_alti = "######0"
    ElseIf nb_decimales = 1 Then
        fmt_alti = "######0.#"
    ElseIf nb_decimales = 2 Then
        fmt_alti = "######0.##"
    ElseIf nb_decimales = 3 Then
        fmt_alti = "######0.###"
    ElseIf nb_decimales = 4 Then
        fmt_alti = "######0.####"
    ElseIf nb_decimales = 5 Then
        fmt_alti = "######0.#####"
    End If
End If
End Sub
'NOM : OgcGetElementGeomAstext
'DESCRIPTION : renvoie la géométrie OGC de l'élément (équivaut à st_astext()) .
'SYNOPSIS
'VOIR EGALEMENT
'DIAGNOSTIC
'___________________________________________________________________________________________________________________________
Public Function OgcGetElementGeomAstext(el As Element, Optional is3d As Boolean = True) As String
Dim pt As Point3d
Dim pts() As Point3d
Dim tg As Integer ' type géométrie: 1=POINT, 2=AREA, 3=LINEAR
Dim i As Integer

If fmt_plani = "" Then
    fmt_plani = "######0.###"
    nb_decimales_plani = 3
End If
If fmt_alti = "" Then
    fmt_alti = "####0.###"
    nb_decimales_alti = 3
End If
If el.IsCellElement Then
    pt = el.AsCellElement.origin
    tg = 1
ElseIf el.IsSharedCellElement Then
    pt = el.AsSharedCellElement.origin
    tg = 1
ElseIf el.IsLineElement Then
    pts = el.AsLineElement.GetVertices
    tg = 3
ElseIf el.IsShapeElement Then
    pts = el.AsShapeElement.GetVertices
    tg = 2
End If

If tg = 1 Then
    If is3d = False Then
        OgcGetElementGeomAstext = "POINT(" + Replace(Format(pt.x, fmt_plani), ",", ".") _
                                            + " " + Replace(Format(pt.y, fmt_plani), ",", ".") + ")"
    Else
        OgcGetElementGeomAstext = "POINTZ(" + Replace(Format(pt.x, fmt_plani), ",", ".") _
                                            + " " + Replace(Format(pt.y, fmt_plani), ",", ".") _
                                            + " " + Replace(Format(pt.z, fmt_alti), ",", ".") + ")"
    End If
ElseIf tg = 2 Then
    If is3d = False Then
        OgcGetElementGeomAstext = "POLYGON(("
        For i = 0 To UBound(pts)
             If i > 0 Then
                 OgcGetElementGeomAstext = OgcGetElementGeomAstext + "," _
                 + Replace(Format(pts(i).x, fmt_plani), ",", ".") + " " _
                 + Replace(Format(pts(i).y, fmt_plani), ",", ".")
             Else
                 OgcGetElementGeomAstext = OgcGetElementGeomAstext + Replace(Format(pts(i).x, fmt_plani), ",", ".") _
                         + " " + Replace(Format(pts(i).y, fmt_plani), ",", ".")
             End If
         Next i
        OgcGetElementGeomAstext = OgcGetElementGeomAstext + "))"
    Else
        OgcGetElementGeomAstext = "POLYGONZ("
        For i = 0 To UBound(pts)
             If i > 0 Then
                 OgcGetElementGeomAstext = OgcGetElementGeomAstext + "," _
                 + Replace(Format(pts(i).x, fmt_plani), ",", ".") + " " _
                 + Replace(Format(pts(i).y, fmt_plani), ",", ".") + " " _
                 + Replace(Format(pts(i).z, fmt_alti), ",", ".")
             Else
                 OgcGetElementGeomAstext = OgcGetElementGeomAstext + Replace(Format(pts(i).x, fmt_plani), ",", ".") _
                         + " " + Replace(Format(pts(i).y, fmt_plani), ",", ".") _
                         + " " + Replace(Format(pts(i).z, fmt_alti), ",", ".")
             End If
         Next i
        OgcGetElementGeomAstext = OgcGetElementGeomAstext + ")"
    End If
ElseIf tg = 3 Then
    If is3d = False Then
        OgcGetElementGeomAstext = "LINESTRING("
        For i = 0 To UBound(pts)
             If i > 0 Then
                 OgcGetElementGeomAstext = OgcGetElementGeomAstext + "," _
                 + Replace(Format(pts(i).x, fmt_plani), ",", ".") + " " _
                 + Replace(Format(pts(i).y, fmt_plani), ",", ".")
             Else
                 OgcGetElementGeomAstext = OgcGetElementGeomAstext + Replace(Format(pts(i).x, fmt_plani), ",", ".") _
                         + " " + Replace(Format(pts(i).y, fmt_plani), ",", ".")
             End If
         Next i
        OgcGetElementGeomAstext = OgcGetElementGeomAstext + ")"
    Else
        OgcGetElementGeomAstext = "LINESTRINGZ("
        For i = 0 To UBound(pts)
             If i > 0 Then
                 OgcGetElementGeomAstext = OgcGetElementGeomAstext + "," _
                 + Replace(Format(pts(i).x, fmt_plani), ",", ".") + " " _
                 + Replace(Format(pts(i).y, fmt_plani), ",", ".") + " " _
                 + Replace(Format(pts(i).z, fmt_alti), ",", ".")
             Else
                 OgcGetElementGeomAstext = OgcGetElementGeomAstext + Replace(Format(pts(i).x, fmt_plani), ",", ".") _
                         + " " + Replace(Format(pts(i).y, fmt_plani), ",", ".") _
                         + " " + Replace(Format(pts(i).z, fmt_alti), ",", ".")
             End If
         Next i
        OgcGetElementGeomAstext = OgcGetElementGeomAstext + ")"
    End If
End If



End Function

Public Function geomTypeFromWkt(wkt As String) As EnumGeomType
Dim length As Integer
Dim s_tmp As String

geomTypeFromWkt = enuGeomTypeUnknown
s_tmp = Mid(wkt, 1, 12)
If InStr(1, s_tmp, "LINESTRING_Z") > 0 Then
    geomTypeFromWkt = enuGeomTypeLine
ElseIf InStr(1, s_tmp, "LINESTRING") > 0 Then
    geomTypeFromWkt = enuGeomTypeLine
ElseIf InStr(1, s_tmp, "POLYGON_Z") > 0 Then
    geomTypeFromWkt = enuGeomTypeArea
ElseIf InStr(1, s_tmp, "POLYGON") > 0 Then
    geomTypeFromWkt = enuGeomTypeArea
ElseIf InStr(1, s_tmp, "POINT_Z") > 0 Then
    geomTypeFromWkt = enuGeomTypePoint
ElseIf InStr(1, s_tmp, "POINT") > 0 Then
    geomTypeFromWkt = enuGeomTypePoint
End If
End Function
Public Function pointElemFromWkt(wkt As String, Optional cellname As String = "CE0101P", Optional cellOrientation As Double = 0#) As Element
Dim myregex As New RegExp
Dim myCollMatch As MatchCollection
Dim myMatch As Match
Dim pt As Point3d
Dim i As Integer
Dim rmat As Matrix3d

wkt = Replace(wkt, "POINT ", "POINT_")

myregex.Global = True
myregex.Pattern = "POINT_Z"
' angles en degrés trigo ?
rmat = Application.Matrix3dFromAxisAndRotationAngle(2, cellOrientation / 180# * Pi)
' forçage cellule si non renseignée
If cellname = "" Then cellname = "CE0101P"
If myregex.Test(wkt) = True Then
    myregex.Pattern = "[.\d]+"
    Set myCollMatch = myregex.Execute(wkt)
    i = 0
    For Each myMatch In myCollMatch
        i = i + 1
        If i = 1 Then
            pt.x = Val(myMatch)
        ElseIf i = 2 Then
            pt.y = Val(myMatch)
        Else
            pt.z = Val(myMatch)
        End If
    Next
    If gUseSharedCell = True Then
        Set pointElemFromWkt = Application.CreateSharedCellElement2(cellname, pt, Application.Point3dOne, True, Application.Matrix3dIdentity)
        elementSetLevel pointElemFromWkt, gLevel
    Else
        Set pointElemFromWkt = Application.CreateCellElement2(cellname, pt, Application.Point3dOne, True, Application.Matrix3dIdentity)
        elementSetLevel pointElemFromWkt, gLevel
    End If
    Exit Function
End If
myregex.Pattern = "POINT"
If myregex.Test(wkt) = True Then
    myregex.Pattern = "[.\d]+"
    Set myCollMatch = myregex.Execute(wkt)
    i = 0
    For Each myMatch In myCollMatch
        i = i + 1
        If i = 1 Then
            pt.x = Val(myMatch)
        ElseIf i = 2 Then
            pt.y = Val(myMatch)
        Else
            pt.z = 0#
        End If
    Next
    If gUseSharedCell = True Then
        Set pointElemFromWkt = Application.CreateSharedCellElement2(cellname, pt, Application.Point3dOne, True, Application.Matrix3dIdentity)
        elementSetLevel pointElemFromWkt, gLevel
    Else
        Set pointElemFromWkt = Application.CreateCellElement2(cellname, pt, Application.Point3dOne, True, Application.Matrix3dIdentity)
        elementSetLevel pointElemFromWkt, gLevel
    End If
    Exit Function
End If

End Function
Public Function lineElemFromWkt(wkt As String) As Element

Dim myregex As New RegExp
Dim myCollMatch As MatchCollection
Dim myMatch As Match
Dim myCollMatch2 As MatchCollection
Dim myMatch2 As Match
Dim pts() As Point3d
Dim i As Integer, j As Integer

wkt = Replace(wkt, "LINESTRING ", "LINESTRING_")
myregex.Global = True
myregex.Pattern = "LINESTRING_Z"
If myregex.Test(wkt) = True Then
    myregex.Pattern = "[-.\d]+ [-.\d]+ [-.\d]+"
    Set myCollMatch2 = myregex.Execute(wkt)
    j = 0
    ReDim pts(0 To myCollMatch2.count - 1)
    For Each myMatch2 In myCollMatch2
        myregex.Pattern = "[.\d]+"
        Set myCollMatch = myregex.Execute(myMatch2)
        i = 0
        For Each myMatch In myCollMatch
            i = i + 1
            If i = 1 Then
                pts(j).x = Val(myMatch)
            ElseIf i = 2 Then
                pts(j).y = Val(myMatch)
            Else
                pts(j).z = Val(myMatch)
            End If
        Next
        j = j + 1
    Next
    Set lineElemFromWkt = Application.CreateLineElement1(Nothing, pts)
    Exit Function
End If
myregex.Pattern = "LINESTRING"
If myregex.Test(wkt) = True Then
    myregex.Pattern = "[.\d]+ [.\d]+"
    Set myCollMatch2 = myregex.Execute(wkt)
    j = 0
    ReDim pts(0 To myCollMatch2.count - 1)
    For Each myMatch2 In myCollMatch2
        myregex.Pattern = "[.\d]+"
        Set myCollMatch = myregex.Execute(myMatch2)
        i = 0
        For Each myMatch In myCollMatch
            i = i + 1
            If i = 1 Then
                pts(j).x = Val(myMatch)
            ElseIf i = 2 Then
                pts(j).y = Val(myMatch)
            Else
                pts(j).z = Val(myMatch)
            End If
        Next
        j = j + 1
    Next
    Set lineElemFromWkt = Application.CreateLineElement1(Nothing, pts)
    Exit Function
End If

End Function
Public Function areaElemFromWkt(wkt As String) As Element

Dim myregex As New RegExp
Dim myCollMatch As MatchCollection
Dim myMatch As Match
Dim myCollMatch2 As MatchCollection
Dim myMatch2 As Match
Dim pts() As Point3d
Dim i As Integer, j As Integer

wkt = Replace(wkt, "POLYGON ", "POLYGON_")

myregex.Global = True
myregex.Pattern = "POLYGON_Z"
If myregex.Test(wkt) = True Then
    myregex.Pattern = "[.\d]+ [.\d]+ [.\d]+"
    Set myCollMatch2 = myregex.Execute(wkt)
    j = 0
    ReDim pts(0 To myCollMatch2.count - 1)
    For Each myMatch2 In myCollMatch2
        myregex.Pattern = "[.\d]+"
        Set myCollMatch = myregex.Execute(myMatch2)
        i = 0
        For Each myMatch In myCollMatch
            i = i + 1
            If i = 1 Then
                pts(j).x = Val(myMatch)
            ElseIf i = 2 Then
                pts(j).y = Val(myMatch)
            Else
                pts(j).z = Val(myMatch)
            End If
        Next
        j = j + 1
    Next
    Set areaElemFromWkt = Application.CreateShapeElement1(Nothing, pts)
    Exit Function
End If
myregex.Pattern = "POLYGON"
If myregex.Test(wkt) = True Then
    myregex.Pattern = "[.\d]+ [.\d]+"
    Set myCollMatch2 = myregex.Execute(wkt)
    j = 0
    ReDim pts(0 To myCollMatch2.count - 1)
    For Each myMatch2 In myCollMatch2
        myregex.Pattern = "[.\d]+"
        Set myCollMatch = myregex.Execute(myMatch2)
        i = 0
        For Each myMatch In myCollMatch
            i = i + 1
            If i = 1 Then
                pts(j).x = Val(myMatch)
            ElseIf i = 2 Then
                pts(j).y = Val(myMatch)
            Else
                pts(j).z = Val(myMatch)
            End If
        Next
        j = j + 1
    Next
    Set areaElemFromWkt = Application.CreateShapeElement1(Nothing, pts)
    Exit Function
End If

End Function
Public Function textElemFromWkt(wkt As String, text As String, Optional textOrientation As Double = 0#) As Element
Dim myregex As New RegExp
Dim myCollMatch As MatchCollection
Dim myMatch As Match
Dim pt As Point3d
Dim i As Integer
Dim rmat As Matrix3d

wkt = Replace(wkt, "POINT ", "POINT_")

myregex.Global = True
myregex.Pattern = "POINT_Z"
' angles en degrés trigo ?
rmat = Application.Matrix3dFromAxisAndRotationAngle(2, textOrientation / 180# * Pi)

If myregex.Test(wkt) = True Then
    myregex.Pattern = "[.\d]+"
    Set myCollMatch = myregex.Execute(wkt)
    i = 0
    For Each myMatch In myCollMatch
        i = i + 1
        If i = 1 Then
            pt.x = Val(myMatch)
        ElseIf i = 2 Then
            pt.y = Val(myMatch)
        Else
            pt.z = Val(myMatch)
        End If
    Next
    Set textElemFromWkt = Application.CreateTextElement1(Nothing, text, pt, Application.Matrix3dIdentity)
    Exit Function
End If
myregex.Pattern = "POINT"
If myregex.Test(wkt) = True Then
    myregex.Pattern = "[.\d]+"
    Set myCollMatch = myregex.Execute(wkt)
    i = 0
    For Each myMatch In myCollMatch
        i = i + 1
        If i = 1 Then
            pt.x = Val(myMatch)
        ElseIf i = 2 Then
            pt.y = Val(myMatch)
        Else
            pt.z = 0#
        End If
    Next
    Set textElemFromWkt = Application.CreateTextElement1(Nothing, text, pt, Application.Matrix3dIdentity)
    Exit Function
End If

End Function
Public Function elemFromWkt(wkt As String) As Element
Dim geomType As EnumGeomType

geomType = geomTypeFromWkt(wkt)

If geomType = enuGeomTypePoint Then
    Set elemFromWkt = pointElemFromWkt(wkt, gCellname, gCellOrientation)
ElseIf geomType = enuGeomTypeLine Then
    Set elemFromWkt = lineElemFromWkt(wkt)
ElseIf geomType = enuGeomTypeArea Then
    Set elemFromWkt = areaElemFromWkt(wkt)
End If

End Function
Public Function geomPointFromXy(ByVal x As Double, ByVal y As Double) As String
If gPgSrid <> 0 Then
    geomPointFromXy = "ST_makePoint( " + wktFromValue(x) + ", " + wktFromValue(y) + "," + CStr(gPgSrid) + ")"
Else
    geomPointFromXy = "ST_makePoint( " + wktFromValue(x) + ", " + wktFromValue(y) + ")"
End If
End Function
Public Function geomPointFromXyz(ByVal x As Double, ByVal y As Double, Optional ByVal z As Double = 0#) As String
If gPgSrid <> 0 Then
    geomPointFromXyz = "ST_makePoint( " + wktFromValue(x) + ", " + wktFromValue(y) + ", " + wktFromValue(z) + ")"
Else
    geomPointFromXyz = "ST_makePoint( " + wktFromValue(x) + ", " + wktFromValue(y) + ", " + wktFromValue(z) + "," + CStr(gPgSrid) + ")"
End If
End Function
Public Function geomFromShapeElement(el As Element) As String
Dim i As Integer
Dim ptArray() As Point3d

ptArray = el.AsShapeElement.GetVertices
If Not el Is Nothing Then
    If el.IsShapeElement Then
        If gPgSrid <> 0 Then
            geomFromShapeElement = "ST_geomFromText( " + wktPolygonFromPointArray(ptArray) + "," + CStr(gPgSrid) + " )"
        Else
            geomFromShapeElement = "ST_geomFromText( " + wktPolygonFromPointArray(ptArray) + " )"
        End If
    End If
End If

End Function
Public Function geomFromFence() As String
Dim i As Integer
Dim el As Element

If Application.ActiveDesignFile.Fence.IsDefined = True Then
  Set el = Application.ActiveDesignFile.Fence.CreateElement
  geomFromFence = geomFromShapeElement(el)
End If

End Function

Public Function wktFromValue(ByVal value As Double) As String
wktFromValue = Replace(Format(value, "########0.0##"), ",", ".")
End Function
Public Function wktLinestringFromPointArray(ptArray() As Point3d, Optional ByVal is3d = False) As String
Dim i As Integer
Dim s_ptArray As String

If is3d = False Then
    For i = 0 To UBound(ptArray)
        If i = 0 Then
          s_ptArray = wktFromValue(ptArray(i).x) + " " + wktFromValue(ptArray(i).y)
        Else
          s_ptArray = s_ptArray + "," + wktFromValue(ptArray(i).x) + " " + wktFromValue(ptArray(i).y)
        End If
    Next i
    wktLinestringFromPointArray = "'LINESTRING ( " + s_ptArray + " )'"
Else
    For i = 0 To UBound(ptArray)
        If i = 0 Then
          s_ptArray = wktFromValue(ptArray(i).x) + " " + wktFromValue(ptArray(i).y) + " " + wktFromValue(ptArray(i).z)
        Else
          s_ptArray = s_ptArray + "," + wktFromValue(ptArray(i).x) + " " + wktFromValue(ptArray(i).y) + " " + wktFromValue(ptArray(i).z)
        End If
    Next i
    wktLinestringFromPointArray = "'LINESTRING_Z ( " + s_ptArray + " )'"
End If

End Function
Public Function wktPolygonFromPointArray(ptArray() As Point3d, Optional ByVal is3d = False) As String
Dim i As Integer
Dim s_ptArray As String

If is3d = False Then
    For i = 0 To UBound(ptArray)
        If i = 0 Then
          s_ptArray = wktFromValue(ptArray(i).x) + " " + wktFromValue(ptArray(i).y)
        Else
          s_ptArray = s_ptArray + "," + wktFromValue(ptArray(i).x) + " " + wktFromValue(ptArray(i).y)
        End If
    Next i
    wktPolygonFromPointArray = "'POLYGON (( " + s_ptArray + " ))'"
Else
    For i = 0 To UBound(ptArray)
        If i = 0 Then
          s_ptArray = wktFromValue(ptArray(i).x) + " " + wktFromValue(ptArray(i).y) + " " + wktFromValue(ptArray(i).z)
        Else
          s_ptArray = s_ptArray + "," + wktFromValue(ptArray(i).x) + " " + wktFromValue(ptArray(i).y) + " " + wktFromValue(ptArray(i).z)
        End If
    Next i
    wktPolygonFromPointArray = "'POLYGON_Z (( " + s_ptArray + " ))'"
End If

End Function


Public Function buildSqlSelectLayerObjects(schemaname As String, tablename As String, srid As Long _
        , Optional sqlWhere As String = "", Optional useFence As Boolean = False) As String
' utiliser clôture (mode bloc)
If useFence = True Then
  Dim s_polygone As String
  Dim s_where As String
  
  s_polygone = geomFromFence()
  If srid <> 0 Then
    s_where = IIf(sqlWhere <> "", _
            sqlWhere + " AND ST_withIn(ST_setSrid(geom," + CStr(srid) + ")," + geomFromFence() + ") = TRUE ", _
            " WHERE ST_withIn(ST_setSrid(geom," + CStr(srid) + ")," + geomFromFence() + ") = TRUE")
  Else
    s_where = IIf(sqlWhere <> "", _
            sqlWhere + " AND ST_withIn(geom," + geomFromFence() + ") = TRUE ", _
            " WHERE ST_withIn(geom," + geomFromFence() + ") = TRUE")
  End If
End If
If s_where <> "" Then
    'gSqlQuery = "SELECT gid , geom_type , d.layer, ST_AsText(geom) FROM " + gTableName _
    + " JOIN ev_cad.description ON d.table_id = " + gTableName
    buildSqlSelectLayerObjects = "SELECT gid, cell_orientation , ST_AsText(geom) AS wkt FROM " + schemaname + ".""" + gTableName + """" + s_where
Else
    buildSqlSelectLayerObjects = "SELECT gid, cell_orientation, ST_AsText(geom) AS wkt FROM " + schemaname + ".""" + gTableName + """"
End If
End Function
Public Function buildSqlSelectLayerLabels(schemaname As String, tablename As String, srid As Long _
        , Optional useFence As Boolean = False) As String
        
Dim sqlWhere As String

' utiliser clôture (mode bloc)
If useFence = True Then
  Dim s_polygone As String
  s_polygone = geomFromFence()
  If srid <> 0 Then
    sqlWhere = " WHERE ""table"" = '" + tablename + "'" _
            + " AND ST_withIn(ST_setSrid(geom," + CStr(srid) + ")," + geomFromFence() + ") = TRUE "
  Else
    sqlWhere = " WHERE ""table"" = '" + tablename + "'" _
            + " AND ST_withIn(geom," + geomFromFence() + ") = TRUE "
  End If
Else
    sqlWhere = " WHERE ""table"" = '" + tablename + "'"
End If
buildSqlSelectLayerLabels = "SELECT gid, label, orientation, size, ST_AsText(geom) AS wkt FROM " + schemaname + ".labels " + sqlWhere
End Function
Public Function buildSqlSelectLayerSettings(schemaname As String, tablename As String) As String
buildSqlSelectLayerSettings = "SELECT cell,cell_orientation,layer,abbr_" + gPgcUserLang + " FROM " + schemaname + ".description" _
            + " WHERE table_id = '" + tablename + "'"
End Function
Public Function buildSqlSelectLayerDescription(schemaname As String, tablename As String) As String
buildSqlSelectLayerDescription = "SELECT abbr_" + gPgcUserLang + " FROM " + schemaname + ".description" _
            + " WHERE table_id = '" + tablename + "'"
End Function
Public Function buildSqlSelectLayerEntitynum(tablename As String) As String
buildSqlSelectLayerEntitynum = "SELECT entitynum FROM mscatalog " _
            + " WHERE tablename = '" + tablename + "'"
End Function
Public Function buildSqlSelectTablenameByEntitynum(entitynum As Integer) As String
buildSqlSelectTablenameByEntitynum = "SELECT tablename FROM mscatalog " _
            + " WHERE entitynum = " + CStr(entitynum)
End Function
Public Function buildSqlSelectTableNameByLayerDescription(schemaname As String, desc As String) As String
buildSqlSelectTableNameByLayerDescription = "SELECT table_id FROM " + schemaname + ".description" _
            + " WHERE abbr_" + gPgcUserLang + " = '" + desc + "'"
End Function
Public Function buildSqlSelectTableNameByLevelnameAndCellname(schemaname As String, levelname As String, Optional cellname As String = "") As String
If cellname <> "" Then
    buildSqlSelectTableNameByLevelnameAndCellname = "SELECT table_id FROM " + schemaname + ".description" _
            + " WHERE layer = '" + levelname + "' AND cell = '" + cellname + "'"
Else
    buildSqlSelectTableNameByLevelnameAndCellname = "SELECT table_id FROM " + schemaname + ".description" _
            + " WHERE layer = '" + levelname + "'"
End If
End Function
Public Function buildLayerKey(tablename As String, desc As String) As String
buildLayerKey = tablename + " :" + desc
End Function
Public Function sendDgnCellToPostgis(tablename As String, el As Element, cellname As String, cell_orientation As Double _
                    , wkt As String, entitynum As Integer, mslink As Long) As Boolean

Dim s_sql As String
Dim vf As Boolean
Dim v_mslink As Variant

If mslink > 0 Then
    s_sql = "UPDATE " + gSchemaName + ".""" + tablename + """ SET  cell_orientation = " + Replace(CStr(cell_orientation), ",", ".") _
                + ", geom = st_geomfromtext('" + wkt + "'," + CStr(gPgSrid) + ")" + " WHERE gid = " + CStr(mslink)
    vf = gPgConnexion.ProcessSQL(s_sql)
Else
    s_sql = "INSERT INTO " + gSchemaName + ".""" + tablename + """ (cell_orientation, geom) VALUES (" _
                + Replace(CStr(cell_orientation), ",", ".") + ", st_geomfromtext('" + wkt + "'," + CStr(gPgSrid) + ")" + " RETURNING gid "
    v_mslink = gPgConnexion.ProcessSQLReturningVariant(s_sql)
    If Not IsNull(v_mslink) Then
        mslink = v_mslink
        Call ElementDbConnectMslink(azidblib.Odbc, el, mslink, entitynum, True)
    End If
End If

End Function
Public Function sendDgnLinearToPostgis(tablename As String, el As Element, wkt As String, entitynum As Integer, mslink As Long) As Boolean

Dim s_sql As String
Dim vf As Boolean
Dim v_mslink As Variant

If mslink > 0 Then
    s_sql = "UPDATE " + gSchemaName + ".""" + tablename + """ SET  geom = st_geomfromtext('" + wkt + "'," + CStr(gPgSrid) + ")" + " WHERE gid = " + CStr(mslink)
    vf = gPgConnexion.ProcessSQL(s_sql)
Else
    s_sql = "INSERT INTO " + gSchemaName + ".""" + tablename + """ (geom) VALUES ( st_geomfromtext('" + wkt + "'," + CStr(gPgSrid) + ")" + " RETURNING gid "
    v_mslink = gPgConnexion.ProcessSQLReturningVariant(s_sql)
    If Not IsNull(v_mslink) Then
        mslink = v_mslink
        Call ElementDbConnectMslink(azidblib.Odbc, el, mslink, entitynum, True)
    End If
End If

End Function
Public Function sendDgnTextToPostgis(tablename As String, el As Element, text As String, size As Double, orientation As Double _
            , wkt As String, entitynum As Integer, mslink As Long) As Boolean

Dim s_sql As String
Dim vf As Boolean
Dim v_mslink As Variant

If mslink > 0 Then
    s_sql = "UPDATE " + gSchemaName + ".description SET ""table"" = '" + tablename + "', text = '" + text + "', orientation = " + Replace(CStr(orientation), ",", ".") _
                + ", size = " + Replace(CStr(size), ",", ".") + ", geom = st_geomfromtext('" + wkt + "'," + CStr(gPgSrid) + ")" + " WHERE gid = " + CStr(mslink)
    vf = gPgConnexion.ProcessSQL(s_sql)
Else
    s_sql = "INSERT INTO " + gSchemaName + ".description (""table"",label,orientation,size,geom) VALUES ('" + tablename + " ','" + text + "'," _
    + Replace(CStr(orientation), ",", ".") + "," + Replace(CStr(size), ",", ".") + " st_geomfromtext('" + wkt + "'," + CStr(gPgSrid) + ")" + " RETURNING gid "
    v_mslink = gPgConnexion.ProcessSQLReturningVariant(s_sql)
    If Not IsNull(v_mslink) Then
        mslink = v_mslink
        Call ElementDbConnectMslink(azidblib.Odbc, el, mslink, entitynum, True)
    End If
End If

End Function

Public Function deleteDgnElementInPostgis(tablename As String, mslink As Long) As Boolean

Dim s_sql As String
Dim vf As Boolean
Dim v_mslink As Variant

If mslink > 0 Then
    s_sql = "DELETE FROM " + gSchemaName + ".""" + tablename + """  WHERE gid = " + CStr(mslink)
    vf = gPgConnexion.ProcessSQL(s_sql)
End If

End Function

Public Function deleteDgnCellInPostgis(tablename As String, mslink As Long) As Boolean

Dim s_sql As String
Dim vf As Boolean
Dim v_mslink As Variant

If mslink > 0 Then
    s_sql = "DELETE FROM " + gSchemaName + ".""" + tablename + """  WHERE gid = " + CStr(mslink)
    vf = gPgConnexion.ProcessSQL(s_sql)
End If

End Function

Public Function deleteDgnLinearInPostgis(tablename As String, mslink As Long) As Boolean

Dim s_sql As String
Dim vf As Boolean
Dim v_mslink As Variant

If mslink > 0 Then
    s_sql = "DELETE FROM " + gSchemaName + ".""" + tablename + """  WHERE gid = " + CStr(mslink)
    vf = gPgConnexion.ProcessSQL(s_sql)
End If

End Function

Public Function deleteDgnTextInPostgis(tablename As String, mslink As Long) As Boolean

Dim s_sql As String
Dim vf As Boolean
Dim v_mslink As Variant

If mslink > 0 Then
    s_sql = "DELETE FROM " + gSchemaName + ".description" + " WHERE gid = " + CStr(mslink)
    vf = gPgConnexion.ProcessSQL(s_sql)
End If

End Function

Attribute VB_Name = "ModulePgconnector"
'/*MAN______________________________________________________________________
'
'
' FICHIER: $RCSfile$ $Revision$
'
'  $Author$  $Date$
'
' DESCRIPTION
' xxxxxxxxxxxxx
'
'
' FONCTIONS
' VOIR EGALEMENT
'
' Copyright   Azimut    Tous droits réservés
' Azimut S.A.R.L 3 rue du travail 67000 Strasbourg
' Tél 03 88 08 50 67
' SIREN 390 458 164   http://www.azimut.fr          grc@azimut.fr
'
'___________________________________________________________________ENDMAN*/
Option Explicit
Public Sub aaa()
Call pointElemFromWkt("POINT_Z (1234567.987 2345678.123 456.876)")
Call lineElemFromWkt("LINESTRING Z (150283.694150877 167516.504080982 0,150284.002511406 167516.203351969 0,150284.288104558 167516.025486892 0,150284.382128906 167516.03805086 0,150284.762990928 167515.238804405 0)")
Call lineElemFromWkt("POLYGON Z (150283.694150877 167516.504080982 0,150284.002511406 167516.203351969 0,150284.288104558 167516.025486892 0,150284.382128906 167516.03805086 0,150284.762990928 167515.238804405 0)")
End Sub
Public Sub pgcNewConnection()
pgcInit
UserFormConnectionSettings.Show
End Sub

Public Sub pgcManageConnection()
pgcInit
UserFormConnectionSettings.Show
End Sub

Public Sub pgcAttachPgLayerDialog()
pgcInit
gCheckoutMode = enuCheckoutModeAttach
UserFormSelectLayer.Show
End Sub

Public Sub pgcAttachPgLayer()
Dim fullname As String
Dim seedfullname As String
Dim vf As Boolean
Dim df As DesignFile
Dim mref As ModelReference
Dim att As Attachment

pgcInit
StopElemsEventHandler
fullname = buildPostgisDgnFilename
If win32api.aziFileMgr.FileExists(fullname) Then
        If gPostgisDgnResetLevel = enuPostgisDgnResetFullFile Then
            vf = win32api.aziFileMgr.EffacerFichier(fullname)
            If vf <> True Then
                Application.MessageCenter.AddMessage l10n(TXT_REINITIALISATION_DU_FICHIER_IMPOSSIBLE), l10n(TXT_LE_FICHIER) + vbCrLf + fullname + vbCrLf + l10n(TXT_NE_PEUT_ETRE_REINITIALISE), msdMessageCenterPriorityError, True
                Application.CommandState.StartDefaultCommand
                Exit Sub
            Else
                vf = pgcCreateActiveDgnPostgis(fullname)
            End If
        Else
            vf = True
        End If
Else
    vf = pgcCreateActiveDgnPostgis(fullname)
End If
If vf = True Then
    On Error GoTo fin
    Err.Clear
    Set df = Application.OpenDesignFileForProgram(fullname, False)
    If df Is Nothing Then
            Application.MessageCenter.AddMessage l10n(TXT_OUVERTURE_DU_FICHIER_IMPOSSIBLE), l10n(TXT_LE_FICHIER) + vbCrLf + fullname + vbCrLf + l10n(TXT_NE_PEUT_ETRE_OUVERT), msdMessageCenterPriorityError, True
            Application.CommandState.StartDefaultCommand
            Exit Sub
    End If
    Set mref = df.DefaultModelReference
    If Not mref Is Nothing Then
        If writeGisObjectsToModel(mref) = True Then
            If gSqlQueryLabels <> "" Then
                Call writeGisLabelsToModel(mref)
            End If
            df.Save
            df.Close
            vf = True
            For Each att In Application.ActiveModelReference.Attachments
                If Not att.IsMissingFile Then
                    If Not att.IsMissingModel Then
                        On Error GoTo suivant
                        If LCase(att.DesignFile.fullname) = LCase(fullname) Then
                            vf = False
                            Exit For
                        End If
                    End If
                End If
suivant:
                On Error GoTo 0
            Next
        Else
            df.Close
        End If
    Else
        df.Close
    End If
    If vf = True Then
        On Error GoTo fin
        Application.ActiveModelReference.Attachments.AddCoincident1 fullname, "Default", PostgisDgnRefLogicalName, l10n(TXT_COUCHES_POSTGIS), msdAddAttachmentElementsVisible + msdAddAttachmentFlagCoincidentWorld
    End If
End If
fin:
    If Err.Number <> 0 Then
        Application.MessageCenter.AddMessage l10n(TXT_ERREUR) + CStr(Err.Number) + "(" = Err.Description + ")", , msdMessageCenterPriorityError, False
    End If
    On Error GoTo 0
End Sub

Public Sub pgcDetachPgLayer()
Dim filename As String, fullname As String

pgcInit
StopElemsEventHandler
fullname = buildPostgisDgnFilename()
filename = Right(fullname, Len(fullname) - InStrRev(fullname, "\"))

If MsgBox(l10n(TXT_TOUTES_LES_COUCHES_POSTGIS_DISPARAITRONT) + vbCrLf + l10n(TXT_VOULEZ_VOUS_DETACHER_LE_FICHIER) + filename + " ?", vbYesNo, l10n(TXT_DETACHER_LES_COUCHES_POSTGIS)) = vbYes Then
    Application.CadInputQueue.SendKeyin "reference detach " + PostgisDgnRefLogicalName
End If

End Sub

Public Sub pgcConnect()
pgcInit
UserFormLogin.Show
End Sub
Public Sub pgcDisconnect()
pgcInit
If Not gPgConnexion Is Nothing Then
    gPgConnexion.Deconnecter
End If
Application.MessageCenter.AddMessage l10n(TXT_DECONNECTE_DE_LA_BD), , msdMessageCenterPriorityInfo, False
End Sub
Public Sub pgcImportPgLayerDialog()
    pgcInit
    gCheckoutMode = enuCheckoutModeImport
    UserFormSelectLayer.Show
End Sub

Public Sub pgcImportPgLayer()
    pgcInit
    StopElemsEventHandler
    If writeGisObjectsToModel(Application.ActiveModelReference) = True Then
        If gSqlQueryLabels <> "" Then
            Call writeGisLabelsToModel(Application.ActiveModelReference)
        End If
        Application.MessageCenter.AddMessage l10n(TXT_COUCHE) + gTableName + l10n(TXT_IMPORTEE_DANS_LE_MODELE_ACTIF), , msdMessageCenterPriorityInfo, False
    Else
        Application.MessageCenter.AddMessage l10n(TXT_ECHEC_DE_L_IMPORT_DE_LA_COUCHE_POSTGIS) + gTableName + l10n(TXT_DANS_LE_MODELE_ACTIF), , msdMessageCenterPriorityError, False
    End If
End Sub
Public Sub pgcExportLevelToPgDialog()
pgcInit
UserFormExport.Show
End Sub

Public Sub pgcExportLevelToPg()
pgcInit
Call sendDgnObjectsToPostgis(gLevel)
End Sub

Public Sub pgcSynchronizingOn()
pgcInit
If Not gPgConnexion Is Nothing Then
    If gPgConnexion.EstConnecte = True Then
        GoTo suite
    End If
End If
Application.MessageCenter.AddMessage l10n(TXT_POUR_UTILISER_CETTE_COMMANDE_VOUS_DEVEZ_ETRE_CONNECTE_A_LA_BD), , msdMessageCenterPriorityError, True
Exit Sub
suite:
InitElemsEventHandler
Application.MessageCenter.AddMessage "SYNCH ON", , msdMessageCenterPriorityWarning, False
End Sub
Public Sub pgcSynchronizingOff()
pgcInit
StopElemsEventHandler
Application.MessageCenter.AddMessage "SYNCH OFF", , msdMessageCenterPriorityWarning, False
End Sub

Attribute VB_Name = "UserFormConnectionSettings"
Attribute VB_Base = "0{D686517F-F68B-4DFF-AC81-E3C12F9CB347}{F080F772-1185-4E38-814E-2E70C8286EC3}"
Attribute VB_GlobalNameSpace = False
Attribute VB_Creatable = False
Attribute VB_PredeclaredId = True
Attribute VB_Exposed = False
Attribute VB_TemplateDerived = False
Attribute VB_Customizable = False
'/*MAN______________________________________________________________________
'
'
' FICHIER: $RCSfile$ $Revision$
'
'  $Author$  $Date$
'
' DESCRIPTION
' xxxxxxxxxxxxx
'
'
' FONCTIONS
' VOIR EGALEMENT
'
' Copyright   Azimut    Tous droits réservés
' Azimut S.A.R.L 3 rue du travail 67000 Strasbourg
' Tél 03 88 08 50 67
' SIREN 390 458 164   http://www.azimut.fr          grc@azimut.fr
'
'___________________________________________________________________ENDMAN*/
Option Explicit
Private Function LoadConnectionSettings(cnxName As String)
Dim s_tmp As String

gPgPassword = ""
Me.TextBoxPwd.text = ""
Me.TextBoxUsr.text = ""

If cnxName <> "" Then
    Me.TextBoxCnxName.text = cnxName
    s_tmp = GetSetting("PgConnector", cnxName, "Host", "")
    If s_tmp <> "" Then
        Me.TextBoxHost.text = s_tmp
    End If
    s_tmp = GetSetting("PgConnector", cnxName, "Port", "")
    If s_tmp <> "" Then
        Me.TextBoxPort.text = s_tmp
    End If
    s_tmp = GetSetting("PgConnector", cnxName, "Dbname", "")
    If s_tmp <> "" Then
        Me.TextBoxDbName.text = s_tmp
    End If
    s_tmp = GetSetting("PgConnector", cnxName, "Username", "")
    If s_tmp <> "" Then
        Me.TextBoxUsr.text = s_tmp
        s_tmp = GetSetting("PgConnector", cnxName, "Password", "")
        If s_tmp <> "" Then
            gPgPassword = s_tmp
            Me.TextBoxPwd.text = String(Len(gPgPassword), "*")
        End If
    End If
Else
    Me.TextBoxCnxName = "IBGE"
    Me.TextBoxHost = "wfs.ibgebim.be"
    Me.TextBoxPort = "5432"
    Me.TextBoxDbName = "ibge"
End If


End Function
Private Function UpdateCnxList(cnxName As String, Optional delete_it As Boolean = False)

Dim cnxNames() As String
Dim found As Boolean
Dim i As Integer

If delete_it = True Then
    If gPgCnxList <> cnxName Then
        gPgCnxList = Replace(gPgCnxList, ";" + cnxName + ";", ";")
        gPgCnxList = Replace(gPgCnxList, ";" + cnxName, "")
        gPgCnxList = Replace(gPgCnxList, cnxName + ";", "")
    Else
        gPgCnxList = ""
    End If
Else
    If gPgCnxList <> "" Then
        cnxNames = Split(gPgCnxList, ";")
        For i = 0 To UBound(cnxNames)
            If cnxName = cnxNames(i) Then
                found = True
                Exit For
            End If
        Next i
        If found = False Then
            gPgCnxList = gPgCnxList + ";" + cnxName
        End If
    Else
        gPgCnxList = cnxName
    End If
End If
End Function
Private Function CheckConnection() As Boolean
Dim azicnx As azidblib.aziDbConnexion
Dim pgOdbcDriver As String

pgOdbcDriver = "PostgreSQL Unicode"
If Application.ActiveWorkspace.IsConfigurationVariableDefined("PGC_ODBC_DRIVER") = True Then
    pgOdbcDriver = Application.ActiveWorkspace.ConfigurationVariableValue("PGC_ODBC_DRIVER")
End If
Set azicnx = azidblib.CreerConnexion
If Me.TextBoxHost.text <> "" And Me.TextBoxPort.text <> "" And Me.TextBoxDbName.text <> "" And Me.TextBoxUsr.text <> "" And gPgPassword <> "" Then
    If checkOpenConnection(azicnx, Me.TextBoxHost.text, Me.TextBoxPort.text, Me.TextBoxDbName.text, Me.TextBoxUsr.text, gPgPassword) = True Then
        CheckConnection = True
    Else
        CheckConnection = False
        MsgBox "Echec de la connexion" + vbCrLf + Err.Description, vbCritical
    End If
End If
Set azicnx = Nothing
End Function

Private Sub CommandButtonCancel_Click()
Me.Hide
Application.CommandState.StartDefaultCommand
End Sub

Private Sub CommandButtonCheckConnection_Click()
If CheckConnection = True Then
    MsgBox l10n(TXT_CONNEXION_A_LA_BD_REUSSIE)
Else
    MsgBox l10n(TXT_ECHEC_DE_LA_CONNEXION_A_LA_BD) + vbCrLf + Err.Description
End If
End Sub

Private Sub CommandButtonDelConnection_Click()
Dim cnxNames() As String
Dim y_or_n As VbMsgBoxResult
Dim defaultCnxName As String
Dim cnxName As String

y_or_n = MsgBox(l10n(TXT_SUPPRIMER_CONNEXION) + " ?", vbYesNo, l10n(TXT_CONNEXION) + " " + PgcVersion)
If y_or_n = vbYes Then
    On Error Resume Next
    Call DeleteSetting("PgConnector", Me.TextBoxCnxName.text)
    On Error GoTo 0
    UpdateCnxList Me.TextBoxCnxName.text, True
    SaveSetting "PgConnector", "Connections", "ConnectionList", gPgCnxList
    
    cnxNames = Split(gPgCnxList, ";")
    If UBound(cnxNames) >= 0 Then
        SaveSetting "PgConnector", "Connections", "ConnectionName", cnxNames(0)
        SaveSetting "PgConnector", "Connections", "DefaultConnectionName", cnxNames(0)
        LoadConnectionSettings cnxNames(0)
    Else
        SaveSetting "PgConnector", "Connections", "ConnectionName", ""
        SaveSetting "PgConnector", "Connections", "DefaultConnectionName", ""
    End If
    
    gPgPassword = ""
    Me.TextBoxPwd.text = ""
    Me.TextBoxUsr.text = ""
End If

End Sub

Private Sub CommandButtonOk_Click()

If Me.TextBoxCnxName.text = "" Then
    MsgBox l10n(TXT_INDIQUER_UN_NOM_POUR_LA_CONNEXION)
    Exit Sub
End If
If CheckConnection = True Then
    SaveSetting "PgConnector", Me.TextBoxCnxName.text, "Host", Me.TextBoxHost.text
    SaveSetting "PgConnector", Me.TextBoxCnxName.text, "Port", Me.TextBoxPort.text
    SaveSetting "PgConnector", Me.TextBoxCnxName.text, "Dbname", Me.TextBoxDbName.text
    If Me.CheckBoxUsr.value = True Then
        SaveSetting "PgConnector", Me.TextBoxCnxName.text, "Username", Me.TextBoxUsr.text
        If Me.CheckBoxPwd.value = True Then
            SaveSetting "PgConnector", Me.TextBoxCnxName.text, "Password", gPgPassword
        End If
    End If
    SaveSetting "PgConnector", "Connections", "ConnectionName", Me.TextBoxCnxName.text
    UpdateCnxList Me.TextBoxCnxName.text
    SaveSetting "PgConnector", "Connections", "ConnectionList", gPgCnxList
    SaveSetting "PgConnector", "Connections", "DefaultConnectionName", Me.TextBoxCnxName.text
    Me.Hide
Else
    MsgBox l10n(TXT_CONNEXION_INVALIDE) + vbCrLf + Err.Description
End If

End Sub


Private Sub TextBoxCnxName_Change()
Dim pgCnxList As String
Dim cnxNames() As String
Dim i As Integer

gPgPassword = ""
Me.TextBoxPwd.text = ""
Me.TextBoxUsr.text = ""
If Me.TextBoxCnxName.text <> "" Then
    pgCnxList = GetSetting("PgConnector", "Connections", "ConnectionList")
    If pgCnxList <> "" Then
        cnxNames = Split(pgCnxList, ";")
        If UBound(cnxNames) >= 0 Then
            For i = 0 To UBound(cnxNames)
                If Me.TextBoxCnxName.text = cnxNames(i) Then
                    LoadConnectionSettings cnxNames(i)
                End If
            Next i
        End If
    End If
End If
End Sub

Private Sub TextBoxPwd_Change()
If Me.TextBoxPwd.text = "" Then
    gPgPassword = ""
Else
    If Right(Me.TextBoxPwd.text, 1) <> "*" Then
        gPgPassword = gPgPassword + Right(Me.TextBoxPwd.text, 1)
        Me.TextBoxPwd.text = String(Len(gPgPassword), "*")
    End If
End If
End Sub





Private Sub UserForm_Activate()

Dim s_tmp As String
Dim cnxName As String

Me.ComboBoxSslMode.Visible = False
Me.ComboBoxSslMode.Enabled = False
Me.Label6.Visible = False
Me.Label6.Enabled = False

gPgPassword = ""
Me.TextBoxPwd.text = ""
Me.TextBoxUsr.text = ""

gPgCnxList = GetSetting("PgConnector", "Connections", "ConnectionList", "")
s_tmp = GetSetting("PgConnector", "Connections", "DefaultConnectionName", "")
LoadConnectionSettings s_tmp

End Sub


Private Sub UserForm_Initialize()

Me.TextBoxCnxName = "Test"
Me.TextBoxHost = "wfs.ibgebim.be"
Me.TextBoxPort = "5432"
Me.TextBoxDbName = "ibge"

Me.Label2.Caption = l10n(TXT_NOM)
Me.Label3.Caption = l10n(TXT_SERVEUR)
Me.Label4.Caption = l10n(TXT_PORT)
Me.Label5.Caption = l10n(TXT_B_D)
Me.Label6.Caption = l10n(TXT_MODE_SSL)
Me.Label7.Caption = l10n(TXT_NOM)
Me.Label8.Caption = l10n(TXT_MOT_DE_PASSE)
Me.Frame1.Caption = l10n(TXT_IDENTIFICATION)
Me.CheckBoxUsr.Caption = l10n(TXT_ENREGISTRER)
Me.CheckBoxPwd.Caption = l10n(TXT_ENREGISTRER)
Me.CommandButtonCheckConnection.Caption = l10n(TXT_TESTER_LA_CONNEXION)

Me.CommandButtonOk.Caption = l10n(TXT_OK)
Me.CommandButtonCancel.Caption = l10n(TXT_QUITTER)
Me.CommandButtonDelConnection.Caption = l10n(TXT_SUPPRIMER_CONNEXION)

Me.Caption = l10n(TXT_CONNEXION) + " " + PgcVersion

End Sub

Attribute VB_Name = "UserFormExport"
Attribute VB_Base = "0{738177F7-E5F8-4435-8FE6-FBD7548E1F51}{EBA4E3BB-FA40-4E9C-9395-ECAC6BF36963}"
Attribute VB_GlobalNameSpace = False
Attribute VB_Creatable = False
Attribute VB_PredeclaredId = True
Attribute VB_Exposed = False
Attribute VB_TemplateDerived = False
Attribute VB_Customizable = False
'/*MAN______________________________________________________________________
'
'
' FICHIER: $RCSfile$ $Revision$
'
'         $Date$
'
' DESCRIPTION
' xxxxxxxxxxxxx
'
'
' FONCTIONS
' VOIR EGALEMENT
'
' Copyright   Azimut    Tous droits réservés
' Azimut S.A.R.L 3 rue du travail 67000 Strasbourg
' Tél 03 88 08 50 67
' SIRET 390 458 164   http://www.azimut.fr          grc@azimut.fr
'
'___________________________________________________________________ENDMAN*/
Option Explicit


Private Sub ComboBoxLevel_Change()
If Me.ComboBoxLevel.ListCount > 0 Then
    If Me.ComboBoxLevel.text <> "" Then
        gLevelName = Me.ComboBoxLevel.text
        Set gLevel = Application.ActiveDesignFile.Levels.Find(gLevelName)
    End If
End If
End Sub

Private Sub ComboBoxSchema_Change()
If Me.ComboBoxSchema.text <> "" Then
    gSchemaName = Me.ComboBoxSchema.text
End If
End Sub

Private Sub CommandButtonCancel_Click()
Me.Hide
Application.CommandState.StartDefaultCommand
End Sub

Private Sub CommandButtonOk_Click()
pgcExportLevelToPg
End Sub

Private Sub UserForm_Activate()
Dim lv As Variant

If Me.ComboBoxLevel.ListCount Then
    Me.ComboBoxLevel.Clear
End If
For Each lv In Application.ActiveModelReference.Levels
    Me.ComboBoxLevel.AddItem lv.name
Next
End Sub

Private Sub UserForm_Initialize()
Dim last_schema As String
Dim i As Integer

'Récupère le nom de la dernière table sélectionnée et l'utilisation de MSCATALOG.
last_schema = GetSetting("PgConnector", "UserFormSelectLayer", "LastSchemaName", "public")

' chargement liste des schémas
If Not gPgConnexion Is Nothing Then
    If gPgConnexion.EstConnecte = True Then
        GoTo suite
    End If
End If
MsgBox "Pour utiliser cette commande, vous devez être connecté à la BD.", vbExclamation
Me.Hide
Application.CommandState.StartDefaultCommand
End
suite:
    For i = 0 To UBound(gSchemasArray)
        Me.ComboBoxSchema.AddItem Trim(gSchemasArray(i))
        If last_schema = Trim(gSchemasArray(i)) Then Me.ComboBoxSchema.ListIndex = i
    Next i
    If Me.ComboBoxSchema.text = "" Then
        Me.ComboBoxSchema.text = gSchemasArray(0)
    End If

Me.Label2.Caption = l10n(TXT_NIVEAU)
Me.Label3.Caption = l10n(TXT_SCHEMA)

Me.CommandButtonOk.Caption = l10n(TXT_OK)
Me.CommandButtonCancel.Caption = l10n(TXT_QUITTER)

Me.Caption = l10n(TXT_EXPORT) + " " + PgcVersion

End Sub

Attribute VB_Name = "UserFormLogin"
Attribute VB_Base = "0{A61595EB-8D55-4BAB-B518-8BDFF1D9F2BD}{84410A0F-CB5B-4BD5-94FE-45BB798C330D}"
Attribute VB_GlobalNameSpace = False
Attribute VB_Creatable = False
Attribute VB_PredeclaredId = True
Attribute VB_Exposed = False
Attribute VB_TemplateDerived = False
Attribute VB_Customizable = False
'/*MAN______________________________________________________________________
'
'
' FICHIER: $RCSfile$ $Revision$
'
'  $Author$  $Date$
'
' DESCRIPTION
' xxxxxxxxxxxxx
'
'
' FONCTIONS
' VOIR EGALEMENT
'
' Copyright   Azimut    Tous droits réservés
' Azimut S.A.R.L 3 rue du travail 67000 Strasbourg
' Tél 03 88 08 50 67
' SIREN 390 458 164   http://www.azimut.fr          grc@azimut.fr
'
'___________________________________________________________________ENDMAN*/
Option Explicit

Private Sub ComboBoxConnection_Change()
gPgConnectionName = Me.ComboBoxConnection.text
If gPgConnectionName <> "" Then
    gPgHost = GetSetting("PgConnector", gPgConnectionName, "Host", "")
    gPgPort = GetSetting("PgConnector", gPgConnectionName, "Port", "")
    gPgDbname = GetSetting("PgConnector", gPgConnectionName, "Dbname", "")
    gPgUsername = GetSetting("PgConnector", gPgConnectionName, "Username", "")
    If gPgUsername <> "" Then
        Me.TextBoxUser.text = gPgUsername
        Me.CheckBoxRecLogin.value = True
        gPgPassword = GetSetting("PgConnector", gPgConnectionName, "Password", "")
        If gPgPassword <> "" Then
            Me.TextBoxPassword.text = String(Len(gPgPassword), "*")
            Me.CheckBoxRecPwd.value = True
        Else
            Me.CheckBoxRecPwd.value = False
        End If
    Else
        Me.CheckBoxRecLogin.value = False
    End If
End If
End Sub

Private Sub CommandButtonCancel_Click()
Me.Hide
Application.CommandState.StartDefaultCommand
End Sub

Private Sub CommandButtonOk_Click()
If gPgConnexion Is Nothing Then
    Set gPgConnexion = azidblib.CreerConnexion
End If
If checkOpenConnection(gPgConnexion, gPgHost, gPgPort, gPgDbname, gPgUsername, gPgPassword) = False Then
    Application.MessageCenter.AddMessage l10n(TXT_ECHEC_CONNEXION_CONTACTEZ_L_ADMINISTRATEUR), l10n(TXT_IMPOSSIBLE_DE_SE_CONNECTER_A_LA_BASE_DE_DONNEES_CONTACTEZ_L_ADMINISTRATEUR_POUR_RESOUDRE_LE_PROBLEME), msdMessageCenterPriorityError, True
    End
Else
    Application.MessageCenter.AddMessage l10n(TXT_CONNECTE_A_LA_BD) + " '" + gPgDbname + "'", , msdMessageCenterPriorityInfo, False
    SaveSetting "PgConnector", "Connections", "ConnectionName", Me.ComboBoxConnection.text
    SaveSetting "PgConnector", "Connections", "DefaultConnectionName", Me.ComboBoxConnection.text
    If Me.CheckBoxRecLogin.value = True Then
        SaveSetting "PgConnector", Me.ComboBoxConnection.text, "Username", Me.TextBoxUser.text
        If Me.CheckBoxRecPwd.value = True Then
            SaveSetting "PgConnector", Me.ComboBoxConnection.text, "Password", gPgPassword
        End If
    End If
    Me.Hide
End If

End Sub

Private Sub TextBoxPassword_Change()
If Me.TextBoxPassword.text = "" Then
    gPgPassword = ""
Else
    If Right(Me.TextBoxPassword.text, 1) <> "*" Then
        gPgPassword = gPgPassword + Right(Me.TextBoxPassword.text, 1)
        Me.TextBoxPassword.text = String(Len(gPgPassword), "*")
    End If
End If
End Sub

Private Sub TextBoxUser_Change()
If Me.TextBoxUser.text <> "" And Me.TextBoxUser.text <> gPgUsername Then
    gPgUsername = Me.TextBoxUser.text
End If
End Sub

Private Sub UserForm_Activate()
Dim s_tmp As String
Dim cnxNames() As String
Dim i As Integer

gPgCnxList = GetSetting("PgConnector", "Connections", "ConnectionList", "")
Me.ComboBoxConnection.Clear
If gPgCnxList <> "" Then
    cnxNames = Split(gPgCnxList, ";")
    For i = 0 To UBound(cnxNames)
        Me.ComboBoxConnection.AddItem cnxNames(i)
    Next i
Else
    MsgBox l10n(TXT_AUCUNE_CONNEXION_DEFINIE_VEUILLEZ_EN_CREER_UNE), vbCritical
    Me.Hide
End If
s_tmp = GetSetting("PgConnector", "Connections", "DefaultConnectionName", "")
If s_tmp <> "" Then
    Me.ComboBoxConnection.text = s_tmp
    gPgConnectionName = s_tmp
    s_tmp = GetSetting("PgConnector", gPgConnectionName, "Host", "")
    If s_tmp <> "" Then
        gPgHost = s_tmp
    End If
    s_tmp = GetSetting("PgConnector", gPgConnectionName, "Port", "")
    If s_tmp <> "" Then
        gPgPort = s_tmp
    End If
    s_tmp = GetSetting("PgConnector", gPgConnectionName, "Dbname", "")
    If s_tmp <> "" Then
        gPgDbname = s_tmp
    End If
    s_tmp = GetSetting("PgConnector", gPgConnectionName, "Username", "")
    If s_tmp <> "" Then
        Me.TextBoxUser.text = s_tmp
        gPgUsername = s_tmp
        s_tmp = GetSetting("PgConnector", gPgConnectionName, "Password", "")
        If s_tmp <> "" Then
            gPgPassword = s_tmp
            Me.TextBoxPassword.text = String(Len(gPgPassword), "*")
            s_tmp = ""
        End If
    End If
End If

End Sub

Private Sub UserForm_Initialize()

Me.Label7.Caption = l10n(TXT_UTILISATEUR)
Me.Label8.Caption = l10n(TXT_MOT_DE_PASSE)
Me.Label9.Caption = l10n(TXT_CONNEXION)
Me.CommandButtonOk.Caption = l10n(TXT_OK)
Me.CommandButtonCancel.Caption = l10n(TXT_QUITTER)

Me.Caption = l10n(TXT_CONNEXION) + " " + PgcVersion

End Sub

Attribute VB_Name = "UserFormSelectLayer"
Attribute VB_Base = "0{BC683F11-D4AC-42A8-9A15-6728479BC127}{F1BA904C-1108-46FA-802C-F4816CA72A44}"
Attribute VB_GlobalNameSpace = False
Attribute VB_Creatable = False
Attribute VB_PredeclaredId = True
Attribute VB_Exposed = False
Attribute VB_TemplateDerived = False
Attribute VB_Customizable = False
'/*MAN______________________________________________________________________
'
'
' FICHIER: $RCSfile$ $Revision$
'
'         $Date$
'
' DESCRIPTION
' xxxxxxxxxxxxx
'
'
' FONCTIONS
' VOIR EGALEMENT
'
' Copyright   Azimut    Tous droits réservés
' Azimut S.A.R.L 3 rue du travail 67000 Strasbourg
' Tél 03 88 08 50 67
' SIRET 390 458 164   http://www.azimut.fr          grc@azimut.fr
'
'___________________________________________________________________ENDMAN*/
Option Explicit


Public Sub updateComboBoxTableWithSchema(schemaname As String, Optional last_table As String = "")
Dim oRecordset As New ADODB.Recordset
Dim sql As String, tablename As String
Dim desc As String
Dim use_table As Boolean
Dim i As Integer

Set oRecordset.ActiveConnection = gPgConnexion.CONNEXION
  ' Ouverture du recordset recensant les tables du (des) schéma(s) par défaut
  sql = "SELECT table_name,table_type FROM information_schema.tables " _
        + " WHERE lower(table_schema) IN ('" & schemaname & "') AND table_type = 'BASE TABLE'" _
        + " ORDER BY table_schema,table_name"
  With oRecordset
    .Open sql, , , adLockReadOnly, adCmdText
  End With


   ' On affiche les tables standards et les vues de l'utilisateur gPgUsername
   If oRecordset.State = adStateOpen Then
    Do While Not oRecordset.EOF
        If oRecordset("table_type") = "TABLE" Or oRecordset("table_type") = "BASE TABLE" Or _
           oRecordset("table_type") = "VIEW" Or _
           oRecordset("table_type") = "LINK" Or oRecordset("table_type") = "PASS-THROUGH" Then
           ' On n'affiche que les tables autorisées en consultation
           tablename = oRecordset("table_name")
           
           ' les noms de tables exploitées sont entièrement en majuscules
           If UCase(tablename) = tablename Then
                use_table = True
           End If
           
           If use_table = True And gPgConnexion.TableExists(tablename) Then
                desc = gPgConnexion.SqlQuery(buildSqlSelectLayerDescription(gSchemaName, tablename))
                Me.ComboBoxTable.AddItem buildLayerKey(tablename, desc)
                gTablenames.Add tablename, buildLayerKey(tablename, desc)
           'ElseIf oRecordset("table_type") = "VIEW" Then
           '      Me.ComboBoxTable.AddItem tablename
           End If
        End If
        oRecordset.MoveNext
      Loop
     End If

If oRecordset.State = adStateOpen Then oRecordset.Close
If Me.ComboBoxTable.ListCount Then
   Me.ComboBoxTable.ListIndex = 0
   ' On fixe la table dernièrement sélectionnée (si elle existe)
   For i = 0 To Me.ComboBoxTable.ListCount - 1
      If UCase$(Me.ComboBoxTable.List(i)) = UCase$(last_table) Then
         Me.ComboBoxTable.ListIndex = i
         Exit For
      End If
   Next
Else
   MsgBox l10n(TXT_AUCUNE_TABLE_N_EST_DISPONIBLE_OU_BIEN_VOUS_N_AVEZ_AUCUN_DROIT_DE_CONSULTATION_SUR_LES_TABLES_EXISTANTES) & Chr$(13) & _
          l10n(TXT_CONTACTEZ_L_ADMINISTRATEUR)
    End
          
End If

End Sub





Private Sub ComboBoxSchema_Change()
If Me.ComboBoxSchema.text <> "" Then
    gSchemaName = Me.ComboBoxSchema.text
    Me.ComboBoxTable.Clear
    If Not gTablenames Is Nothing Then
        Set gTablenames = Nothing
    End If
    Set gTablenames = New Collection
    ' update ComboBoxTable
    updateComboBoxTableWithSchema (gSchemaName)
End If
End Sub

Private Sub ComboBoxTable_Change()
Dim tablename As String
On Error GoTo fin
tablename = gTablenames(Me.ComboBoxTable.text)
If gTableName <> tablename Then
    gTableName = tablename
    gEntitynum = gPgConnexion.SqlQuery(buildSqlSelectLayerEntitynum(tablename))
    gSqlQuery = ""
    gSqlWhere = ""
    gSqlWhereUser = ""
    gSqlWhereFence = ""
End If
fin:
End Sub

Private Sub CommandButtonOk_Click()
  Dim tablename As String
  Dim schemaname As String
  Dim s_tmp As String
   
  Me.OptionButtonNone.TripleState = False
  Me.OptionButtonLayerOnly.TripleState = True
  Me.OptionButtonFullFile.TripleState = False
    
  ' Sauvegarde le nom de la dernière table sélectionnée et l'utilisation de MSCATALOG.
  SaveSetting "PgConnector", "UserFormSelectLayer", "LastTableName", gTableName
  SaveSetting "PgConnector", "UserFormSelectLayer", "LastSchemaName", gSchemaName
   ' Enregistrement de la position de la fenètre dans la base de registre
  SaveSetting "PgConnector", "UserFormSelectLayer", "top", Me.Top
  SaveSetting "PgConnector", "UserFormSelectLayer", "left", Me.Left
    
' SRID
gPgSrid = getLayerSrid(gSchemaName, gTableName)

' requete
gSqlWhere = ""

If gSqlWhereUser <> "" Then
    gSqlWhere = " WHERE " + gSqlWhereUser
End If

gSqlQueryLabels = ""
' utiliser clôture (mode bloc)
If Me.CheckBoxUseFence.value = True And Application.ActiveDesignFile.Fence.IsDefined = True Then
    gSqlQuery = buildSqlSelectLayerObjects(gSchemaName, gTableName, gPgSrid, gSqlWhereUser, True)
    If Me.CheckBoxLabels.value = True Then
        gSqlQueryLabels = buildSqlSelectLayerLabels(gSchemaName, gTableName, gPgSrid, True)
    End If
Else
    gSqlQuery = buildSqlSelectLayerObjects(gSchemaName, gTableName, gPgSrid, gSqlWhereUser, False)
    If Me.CheckBoxLabels.value = True Then
        gSqlQueryLabels = buildSqlSelectLayerLabels(gSchemaName, gTableName, gPgSrid, False)
    End If
End If

'gSqlQuery = gSqlQuery + " LIMIT 19"
If gCheckoutMode = enuCheckoutModeImport Then
    Call pgcImportPgLayer
Else
    Call pgcAttachPgLayer
End If

End Sub

Private Sub CommandButtonCancel_Click()
Me.Hide
Application.CommandState.StartDefaultCommand
End Sub



Private Sub OptionButtonFullFile_Click()
gPostgisDgnResetLevel = enuPostgisDgnResetFullFile
Me.OptionButtonNone.value = False
Me.OptionButtonLayerOnly.value = False
Me.OptionButtonFullFile.value = True
End Sub

Private Sub OptionButtonLayerOnly_Click()
gPostgisDgnResetLevel = enuPostgisDgnResetLayerOnly
Me.OptionButtonNone.value = False
Me.OptionButtonLayerOnly.value = True
Me.OptionButtonFullFile.value = False
End Sub

Private Sub OptionButtonNone_Click()
gPostgisDgnResetLevel = enuPostgisDgnResetNone
Me.OptionButtonNone.value = True
Me.OptionButtonLayerOnly.value = False
Me.OptionButtonFullFile.value = False
End Sub

Private Sub TextBoxWhere_Change()
gSqlWhereUser = Me.TextBoxWhere
End Sub

Private Sub UserForm_Activate()
If gCheckoutMode = enuCheckoutModeImport Then
    Me.Caption = l10n(TXT_IMPORTER_COUCHE_POSTGIS) + " " + PgcVersion
    Me.OptionButtonNone.Top = 12
    Me.OptionButtonLayerOnly.Top = 36
    Me.OptionButtonFullFile.Top = 128
Else
    Me.Caption = l10n(TXT_ATTACHER_COUCHE_POSTGIS_EN_REFERENCE) + " " + PgcVersion
    Me.OptionButtonNone.Top = 6
    Me.OptionButtonLayerOnly.Top = 24
    Me.OptionButtonFullFile.Top = 48
End If
End Sub

Private Sub UserForm_Initialize()

Dim oRecordset As ADODB.Recordset
Dim sql As String
Dim i As Integer
Dim tablename As String
Dim table_arr() As String
Dim j As Integer
Dim last_table As String
Dim last_schema As String
Dim use_table As Boolean
Dim lngLeft As Long
Dim lngTop As Long
Dim schemas_names As String
Dim schemas_arr() As String

'Récupère la dernière position de la feuille. Cette position est enregistrée dans une clé du registre
'Il faut penser à mettre la propriété startUpPosition en Manuel
lngTop = GetSetting("PgConnector", "UserFormSelectLayer", "Top", "200")
lngLeft = GetSetting("PgConnector", "UserFormSelectLayer", "Left", "300")
Me.Move lngLeft, lngTop

Me.ComboBoxTable.Clear

'Récupère le nom de la dernière table sélectionnée.
last_table = GetSetting("PgConnector", "UserFormSelectLayer", "LastTableName", "")
last_schema = GetSetting("PgConnector", "UserFormSelectLayer", "LastSchemaName", "Utilisateur")

' chargement liste des schémas
If Not gPgConnexion Is Nothing Then
    If gPgConnexion.EstConnecte = True Then
        GoTo suite
    End If
End If
MsgBox "Pour utiliser cette commande, vous devez être connecté à la BD.", vbExclamation
Me.Hide
Application.CommandState.StartDefaultCommand
End
suite:
    Set oRecordset = New Recordset
    For i = 0 To UBound(gSchemasArray)
        Me.ComboBoxSchema.AddItem Trim(gSchemasArray(i))
        If last_schema = Trim(gSchemasArray(i)) Then Me.ComboBoxSchema.ListIndex = i
    Next i
    If Me.ComboBoxSchema.text = "" Then
        Me.ComboBoxSchema.text = gSchemasArray(0)
    End If


If Me.ComboBoxTable.ListCount < 1 Then
   MsgBox l10n(TXT_AUCUNE_TABLE_N_EST_DISPONIBLE_OU_BIEN_VOUS_N_AVEZ_AUCUN_DROIT_DE_CONSULTATION_SUR_LES_TABLES_EXISTANTES) & Chr$(13) & _
          l10n(TXT_CONTACTEZ_L_ADMINISTRATEUR)
    End
End If

Me.OptionButtonNone.value = True

gPgSrid = PgDefaultSrid

Me.Label2.Caption = l10n(TXT_SCHEMA)
Me.Label1.Caption = l10n(TXT_TABLE)
Me.Frame1.Caption = l10n(TXT_FILTRE)
Me.Frame2.Caption = l10n(TXT_REINITIALISER)

Me.CheckBoxLabels.Caption = l10n(TXT_LABELS)
Me.CheckBoxUseFence.Caption = l10n(TXT_UTILISER_CLOTURE)

Me.OptionButtonFullFile.Caption = l10n(TXT_FICHIER_ENTIER)
Me.OptionButtonLayerOnly.Caption = l10n(TXT_COUCHE_SEULEMENT)
Me.OptionButtonNone.Caption = l10n(TXT_AUCUNE)

Me.CommandButtonOk.Caption = l10n(TXT_OK)
Me.CommandButtonCancel.Caption = l10n(TXT_QUITTER)

End Sub
